IANA-PWE3-MIB DEFINITIONS ::= BEGIN 
     
    IMPORTS 
        MODULE-IDENTITY, transmission, enterprises 
           FROM SNMPv2-SMI -- [RFC2578] 
     
        TEXTUAL-CONVENTION 
           FROM SNMPv2-TC; -- [RFC2579] 
     
    ianaPwe3MIB  MODULE-IDENTITY 
        LAST-UPDATED "200601110000Z" --  January 11, 2006 
        ORGANIZATION "IANA" 
        CONTACT-INFO 
             "Internet Assigned Numbers Authority 
             Internet Corporation for Assigned Names and Numbers 
             4676 Admiralty Way, Suite 330 
             Marina del Rey, CA 90292-6601 
     
             Phone: +1 310 823 9358 

             EMail: iana@iana.org" 
        DESCRIPTION 
            "This MIB module defines the IANAPwTypeTC and 
            IANAPwPsnTypeTC textual conventions for use in PWE3 
            MIB modules. 
     
            Any additions or changes to the contents of this MIB 
            module require either publication of an RFC, Designated  
            Expert Review as defined in RFC 2434, Guidelines for  
            Writing an IANA Considerations Section in RFCs, and should  
            be based on the procedures defined in [PWE3IANA]. The  
            Designated Expert will be selected by the IESG Area  
            Director(s) of the internet Area." 
     
        REVISION     "200601110000Z" --  January 11, 2006  
        DESCRIPTION  "Original version, published as part of RFC 
    XXXX." 
    -- RFC Editor: please fill the XXXX and remove this note. 
     
        ::= {enterprises futuresoftware (2076) futureMpls (13) 3 } 
    -- RFC Editor: please fill the YYYY based on the IANA allocation 
    -- and remove this note. 
     
    IANAPwTypeTC ::= TEXTUAL-CONVENTION  
       STATUS     current  
       DESCRIPTION  
          "Indicates the PW type (i.e. the carried service). " 
     SYNTAX   INTEGER {  
        other(0),  
        frameRelayDlci(1),  
        atmAal5SduVcc(2),  
        atmTransparent(3),  
        ethernetTagged(4),  
        ethernet(5),  
        hdlc(6),  
        ppp(7),  
        cem(8),  -- old format  
        atmCellNto1Vcc(9),  
        atmCellNto1Vpc(10),  
        ipLayer2Transport(11),  
        atmCell1to1Vcc(12),  
        atmCell1to1Vpc(13),  
        atmAal5PduVcc(14),  
        frameRelayPortMode(15),  
        cep(16),  
        e1Satop(17),  
        t1Satop(18),  
        e3Satop(19),  
        t3Satop(20),  
        basicCesPsn(21),  
        basicTdmIp(22),  
        tdmCasCesPsn(23),  
        tdmCasTdmIp(24), 
        frDlci(25)  
         }        
     
    IANAPwPsnTypeTC ::= TEXTUAL-CONVENTION  
       STATUS      current  
       DESCRIPTION 
          "Identifies the PSN type which the PW will use over the  
           network." 
       SYNTAX   INTEGER {  
          mpls       (1),   
          l2tp       (2),  
          ip         (3),  
          mplsOverIp (4),   
          gre        (5),  
          other      (6)  
          } 
    END
