-- Copyright (C) 2010-2012 Aricent Group . All Rights Reserved

-- $Id: fsstdbfdtc.mib,v 1.2 2012/09/07 09:52:06 siva Exp $
-- BFD-STD-TC-MIB

BFD-TC-STD-MIB DEFINITIONS ::= BEGIN

    IMPORTS
        MODULE-IDENTITY, enterprises, Unsigned32
            FROM SNMPv2-SMI                                 -- [RFC2578]

        TEXTUAL-CONVENTION
            FROM SNMPv2-TC;                                 -- [RFC2579]

    bfdTCStdMib MODULE-IDENTITY
        LAST-UPDATED "201209050000Z"
        ORGANIZATION "ARICENT COMMUNICATIONS SOFTWARE"
        CONTACT-INFO "support@aricent.com"
        DESCRIPTION
            "This MIB module defines TEXTUAL-CONVENTIONs for concepts
             used in Bidirectional Forwarding Detection (BFD)

             protocols."
        REVISION "201209050000Z"
        DESCRIPTION
            "Initial version."
    ::= { enterprises aricent-communication-holding-ltd(29601) iss(2) 60 }
 -- RFC Ed.: assigned by IANA, see section 5 for details

    BfdSessIndexTC ::= TEXTUAL-CONVENTION
    DISPLAY-HINT   "d"
    STATUS         current
    DESCRIPTION
        "An index used to uniquely identify BFD sessions."
    SYNTAX Unsigned32 (1..4294967295)

    BfdIntervalTC ::= TEXTUAL-CONVENTION
    DISPLAY-HINT  "d"
    STATUS        current
    DESCRIPTION
        "The BFD interval in microseconds."
    SYNTAX Unsigned32 (0..4294967295)

    BfdMultiplierTC ::= TEXTUAL-CONVENTION
    DISPLAY-HINT    "d"
    STATUS          current
    DESCRIPTION
        "The BFD failure detection multiplier."
    SYNTAX Unsigned32 (1..255)

    BfdDiagTC ::= TEXTUAL-CONVENTION
    STATUS       current
    DESCRIPTION
        "A common BFD diagnostic code."
    SYNTAX INTEGER {
        noDiagnostic(0),
        controlDetectionTimeExpired(1),
        echoFunctionFailed(2),
        neighborSignaledSessionDown(3),
        forwardingPlaneReset(4),
        pathDown(5),
        concatenatedPathDown(6),
        administrativelyDown(7),
        reverseConcatenatedPathDown(8)
    }

    BfdSessTypeTC ::= TEXTUAL-CONVENTION
    STATUS        current
    DESCRIPTION
        "BFD session type"

    REFERENCE
        "RFC5880, RFC5881, RFC5883"
    SYNTAX INTEGER {
        singleHop(1),
        multiHopTotallyArbitraryPaths(2),
        multiHopOutOfBandSignaling(3),
        multiHopUnidirectionalLinks(4),
        multiPointHead(5),
        multiPointTail(6)
    }

    BfdSessOperModeTC ::= TEXTUAL-CONVENTION
    STATUS            current
    DESCRIPTION
        "BFD session operating mode"
    REFERENCE
        "RFC5880, Section 3.2"
    SYNTAX INTEGER {
        asyncModeWEchoFunction(1),
        asynchModeWOEchoFunction(2),
        demandModeWEchoFunction(3),
        demandModeWOEchoFunction(4)
    }

    BfdCtrlDestPortNumberTC ::= TEXTUAL-CONVENTION
    DISPLAY-HINT            "d"
    STATUS                  current
    DESCRIPTION
        "UDP destination port number of BFD control packets.
         3784 represents single hop BFD session.
         4784 represents multi hop BFD session.
         However, syntax is left open to wider range of values
         purposely for two reasons:
         1. implementation uses non-compliant port number for
            valid proprietary reason.
         2. potential future extension drafts."
    REFERENCE
        "Port 3784 (RFC5881) and Port 4784 (RFC5883)"
    SYNTAX Unsigned32 (0..65535)

    BfdCtrlSourcePortNumberTC ::= TEXTUAL-CONVENTION
    DISPLAY-HINT              "d"
    STATUS                    current
    DESCRIPTION
        "UDP source port number of BFD control packets.
         However, syntax is left open to wider range of values
         purposely for two reasons:
         1. implementation uses non-compliant port number for
            valid proprietary reason.

         2. potential future extension drafts."
    REFERENCE
        "Port 49152..65535 (RFC5881)"
    SYNTAX Unsigned32 (0..65535)

    BfdSessStateTC ::= TEXTUAL-CONVENTION
    STATUS         current
    DESCRIPTION
        "BFD session state. State failing(5) is only applicable if
         corresponding session is running in BFD version 0."
    REFERENCE
        "draft-katz-ward-bfd-02.txt, RFC5880"
    SYNTAX INTEGER {
        adminDown(1),
        down(2),
        init(3),
        up(4),
        failing(5)
    }

    BfdSessAuthenticationTypeTC ::= TEXTUAL-CONVENTION
    STATUS                      current
    DESCRIPTION
        "BFD authentication type"
    REFERENCE
        "RFC5880, Sections 4.2 - 4.4"
    SYNTAX INTEGER {
        noAuthentication(-1),
        reserved(0),
        simplePassword(1),
        keyedMD5(2),
        meticulousKeyedMD5(3),
        keyedSHA1(4),
        meticulousKeyedSHA1(5)
    }

    BfdSessionAuthenticationKeyTC ::= TEXTUAL-CONVENTION
    DISPLAY-HINT                  "1x "
    STATUS                        current
    DESCRIPTION
        "BFD authentication key type.
    
         A BfdSessionAuthenticationKeyTC is always interpreted within
         the context of an BfdSessAuthenticationTypeTC value.  Every
         usage of the BfdSessionAuthenticationTypeTC textual
         convention is required to specify the the
         BfdSessionAuthenticationKeyTC object that provides the
         context.  It is suggested that the
         BfdSessionAuthentcationTypeTC object be logically registered

         before the object(s) that use the
         BfdSessionAuthenticationKeyTC textual convention, if they
         appear in the same logical row.

         The value of a BfdSessionAuthenticationKeyTC must always be
         consistent with the value of the associated
         BfdSessionAuthencationTypeTC object.  Attempts to set a
         BfdSessionAuthenticationKeyTC object to a value inconsistent
         with the associated BfdSessionAuthenticationTypeTC must fail
         with an inconsistentValue error.

         The following size constraints for a
         BfdSessionAuthenticationKeyTC object are defined for the
         associated BfdSessionAuthenticationTypeTC values show below:

         noAuthentication(-1): SIZE(0)
         reserved(0): SIZE(0)
         simplePassword(1): SIZE(1..16)
         keyedMD5(2): SIZE(16)
         meticulousKeyedMD5(3): SIZE(16)
         keyedSHA1(4): SIZE(20)
         meticulousKeyedSHA1(5): SIZE(20)

         When this textual convention is used as the syntax of an
         index object, there may be issues with the limit of 128
         sub-identifiers specified in SMIv2, STD 58.  In this case,
         the object definition MUST include a 'SIZE' clause to limit
         the number of potential instance sub-identifiers; otherwise
         the applicable constraints MUST be stated in the appropriate
         conceptual row DESCRIPTION clauses, or in the surrounding
         documentation if there is no single DESCRIPTION clause that
         is appropriate."
    REFERENCE
        "RFC5880, Sections 4.2 - 4.4"
    SYNTAX OCTET STRING(SIZE(0..252))

    END
