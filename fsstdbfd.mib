-- Copyright (C) 2010-2012 Aricent Group . All Rights Reserved

-- $Id: fsstdbfd.mib,v 1.3 2012/09/07 09:52:06 siva Exp $

-- BFD-STD-MIB
 
   BFD-STD-MIB DEFINITIONS ::= BEGIN

    IMPORTS
        MODULE-IDENTITY, OBJECT-TYPE, NOTIFICATION-TYPE,
            enterprises, Integer32, Unsigned32, Counter32, Counter64
            FROM SNMPv2-SMI

        TruthValue, RowStatus, StorageType, TimeStamp
            FROM SNMPv2-TC

        MODULE-COMPLIANCE, OBJECT-GROUP, NOTIFICATION-GROUP
            FROM SNMPv2-CONF

        InterfaceIndexOrZero
            FROM IF-MIB

        InetAddress, InetAddressType, InetPortNumber
            FROM INET-ADDRESS-MIB

        BfdSessIndexTC, BfdIntervalTC, BfdMultiplierTC, BfdDiagTC,
        BfdSessTypeTC, BfdSessOperModeTC, BfdCtrlDestPortNumberTC,
        BfdCtrlSourcePortNumberTC, BfdSessStateTC,BfdSessAuthenticationTypeTC,
  	BfdSessionAuthenticationKeyTC
            FROM BFD-TC-STD-MIB;

    bfdMIB MODULE-IDENTITY
        LAST-UPDATED "201209050000Z"
        ORGANIZATION "ARICENT COMMUNICATIONS SOFTWARE"
        CONTACT-INFO "support@aricent.com"
        DESCRIPTION
            "Bidirectional Forwarding Management Information Base."
        REVISION "201209050000Z"
        DESCRIPTION
            "Initial version."

        ::= { enterprises aricent-communication-holding-ltd(29601) iss(2) 56 }

 -- Top level components of this MIB module.

    bfdNotifications OBJECT IDENTIFIER ::= { bfdMIB 0 }

    bfdObjects       OBJECT IDENTIFIER ::= { bfdMIB 1 }

    bfdConformance   OBJECT IDENTIFIER ::= { bfdMIB 2 }

    bfdScalarObjects OBJECT IDENTIFIER ::= { bfdObjects 1 }

 -- BFD General Variables

 -- These parameters apply globally to the Systems'
 -- BFD Process.

    bfdAdminStatus OBJECT-TYPE
        SYNTAX     INTEGER {
            enabled(1),
            disabled(2)
        }
        MAX-ACCESS read-write
	STATUS     current
        DESCRIPTION
            "The global administrative status of BFD in this router.
             The value 'enabled' denotes that the BFD Process is
             active on at least one interface; 'disabled' disables
             it on all interfaces."
        DEFVAL { enabled }
        ::= { bfdScalarObjects 1 }

    bfdSessNotificationsEnable OBJECT-TYPE
        SYNTAX     TruthValue
        MAX-ACCESS read-write
        STATUS     current
        DESCRIPTION
            "If this object is set to true(1), then it enables
             the emission of bfdSessUp and bfdSessDown
             notifications; otherwise these notifications are not
             emitted."
        REFERENCE
            "See also RFC3413 for explanation that
             notifications are under the ultimate control of the
             MIB modules in this document."
        DEFVAL { false }
        ::= { bfdScalarObjects 2 }

 -- BFD Session Table
 -- The BFD Session Table specifies BFD session specific
 -- information.

    bfdSessTable OBJECT-TYPE
        SYNTAX     SEQUENCE OF BfdSessEntry
        MAX-ACCESS not-accessible
        STATUS     current
        DESCRIPTION
            "The BFD Session Table describes the BFD sessions."
        REFERENCE
            "BFD Version 0 (draft-katz-ward-bfd-02.txt) and
             BFD Version 1 (RFC5880)"
        ::= { bfdObjects 2 }

    bfdSessEntry OBJECT-TYPE
        SYNTAX     BfdSessEntry
        MAX-ACCESS not-accessible
        STATUS     current
        DESCRIPTION
            "The BFD Session Entry describes BFD session."
        INDEX { bfdSessIndex }
        ::= { bfdSessTable 1 }

    BfdSessEntry ::= SEQUENCE {
        bfdSessIndex                    BfdSessIndexTC,
        bfdSessVersionNumber            Unsigned32,
        bfdSessType                     BfdSessTypeTC,
        bfdSessDiscriminator            Unsigned32,
        bfdSessRemoteDiscr              Unsigned32,
        bfdSessDestinationUdpPort       BfdCtrlDestPortNumberTC,
        bfdSessSourceUdpPort            BfdCtrlSourcePortNumberTC,
        bfdSessEchoSourceUdpPort        InetPortNumber,
        bfdSessAdminStatus              INTEGER,
        bfdSessState                    BfdSessStateTC,
        bfdSessRemoteHeardFlag          TruthValue,
        bfdSessDiag                     BfdDiagTC,
        bfdSessOperMode                 BfdSessOperModeTC,
        bfdSessDemandModeDesiredFlag    TruthValue,
        bfdSessControlPlaneIndepFlag    TruthValue,
        bfdSessMultipointFlag           TruthValue,
        bfdSessInterface                InterfaceIndexOrZero,
        bfdSessSrcAddrType              InetAddressType,
        bfdSessSrcAddr                  InetAddress,
        bfdSessDstAddrType              InetAddressType,
        bfdSessDstAddr                  InetAddress,
        bfdSessGTSM                     TruthValue,
        bfdSessGTSMTTL                  Unsigned32,
        bfdSessDesiredMinTxInterval     BfdIntervalTC,
        bfdSessReqMinRxInterval         BfdIntervalTC,
        bfdSessReqMinEchoRxInterval     BfdIntervalTC,
        bfdSessDetectMult               BfdMultiplierTC,
        bfdSessNegotiatedInterval       BfdIntervalTC,
        bfdSessNegotiatedEchoInterval   BfdIntervalTC,
        bfdSessNegotiatedDetectMult     BfdMultiplierTC,
        bfdSessAuthPresFlag             TruthValue,
        bfdSessAuthenticationType       BfdSessAuthenticationTypeTC,
        bfdSessAuthenticationKeyID      Integer32,
        bfdSessAuthenticationKey        BfdSessionAuthenticationKeyTC,
        bfdSessStorType                 StorageType,
        bfdSessRowStatus                RowStatus
    }

    bfdSessIndex OBJECT-TYPE
        SYNTAX     BfdSessIndexTC
        MAX-ACCESS not-accessible
        STATUS     current
        DESCRIPTION
            "This object contains an index used to represent a
             unique BFD session on this device."
        ::= { bfdSessEntry 1 }

    bfdSessVersionNumber OBJECT-TYPE
        SYNTAX     Unsigned32 (0..7)
        MAX-ACCESS read-create
        STATUS     current
        DESCRIPTION
            "The version number of the BFD protocol that this session
             is running in. Write access is available for this object
             to provide ability to set desired version for this
             BFD session."
        REFERENCE
            "BFD Version 0 (draft-katz-ward-bfd-02.txt) and
             BFD Version 1 (RFC5880)"
        DEFVAL { 1 }
        ::= { bfdSessEntry 2 }

    bfdSessType OBJECT-TYPE
        SYNTAX     BfdSessTypeTC
        MAX-ACCESS read-create
        STATUS     current
        DESCRIPTION
            "This object specifies the type of this BFD session."
        ::= { bfdSessEntry 3 }

    bfdSessDiscriminator OBJECT-TYPE
        SYNTAX     Unsigned32 (1..4294967295)
        MAX-ACCESS read-only
        STATUS     current
        DESCRIPTION
            "This object specifies the local discriminator for this BFD
             session, used to uniquely identify it."
        ::= { bfdSessEntry 4 }

    bfdSessRemoteDiscr OBJECT-TYPE
        SYNTAX     Unsigned32 (0 | 1..4294967295)
        MAX-ACCESS read-only
        STATUS     current
        DESCRIPTION
            "This object specifies the session discriminator chosen
             by the remote system for this BFD session.  The value may
             be zero(0) if the remote discriminator is not yet known
             or if the session is in the down or adminDown(1) state."
        REFERENCE
            "RFC5880, Section 6.8.6"
        ::= { bfdSessEntry 5 }

    bfdSessDestinationUdpPort OBJECT-TYPE
        SYNTAX     BfdCtrlDestPortNumberTC
        MAX-ACCESS read-create
        STATUS     current
        DESCRIPTION
            "This object specifies the destination UDP port number
             used for this BFD session's control packets. The value
             may be zero(0) if the session is in adminDown(1) state."
        DEFVAL { 0 }
        ::= { bfdSessEntry 6 }

    bfdSessSourceUdpPort OBJECT-TYPE
        SYNTAX     BfdCtrlSourcePortNumberTC
        MAX-ACCESS read-create
        STATUS     current
        DESCRIPTION
            "This object specifies the source UDP port number used
             for this BFD session's control packets. The value may be
             zero(0) if the session is in adminDown(1) state. Upon
             creation of a new BFD session via this MIB, the value of
             zero(0) specified would permit the implementation to
             chose its own source port number."
        DEFVAL { 0 }
        ::= { bfdSessEntry 7 }

    bfdSessEchoSourceUdpPort OBJECT-TYPE
        SYNTAX     InetPortNumber
        MAX-ACCESS read-create
        STATUS     current
        DESCRIPTION
            "This object specifies the source UDP port number used for
             this BFD session's echo packets. The value may be zero(0)
             if the session is not running in the echo mode, or the
             session is in adminDown(1) state. Upon creation of a new
             BFD session via this MIB, the value of zero(0) would
             permit the implementation to chose its own source port
             number."
        DEFVAL { 0 }
        ::= { bfdSessEntry 8 }

    bfdSessAdminStatus OBJECT-TYPE
        SYNTAX     INTEGER {
                            stop(1),
                            start(2)
                   }
        MAX-ACCESS read-create
        STATUS     current
        DESCRIPTION
                "A transition from 'stop' to 'start' will start
                 the BFD state machine for the session. The state
                 machine will have an initial state of down.
                 A transition from 'start' to 'stop' will cause
                 the BFD sesssion to be brought down to
                 adminDown(1). Care should be used in providing
                 write access to this object without adequate
                 authentication."
        DEFVAL { 2 }
        ::= { bfdSessEntry 9 }

    bfdSessState OBJECT-TYPE
        SYNTAX     BfdSessStateTC
        MAX-ACCESS read-only
        STATUS     current
        DESCRIPTION
            "BFD session state."
        DEFVAL { 2 }
        ::= { bfdSessEntry 10 }

    bfdSessRemoteHeardFlag OBJECT-TYPE
        SYNTAX     TruthValue
        MAX-ACCESS read-only
        STATUS     current
        DESCRIPTION
            "This object specifies status of BFD packet reception from
             the remote system. Specifically, it is set to true(1) if
             the local system is actively receiving BFD packets from  
             the remote system, and is set to false(2) if the local  
             system has not received BFD packets recently (within the   
             detection time) or if the local system is attempting to   
             tear down the BFD session."
        REFERENCE
            "BFD Version 0 (draft-katz-ward-bfd-02.txt) and
             BFD Version 1 (RFC5880)"
        DEFVAL { false }
        ::= { bfdSessEntry 11 }

    bfdSessDiag OBJECT-TYPE
        SYNTAX     BfdDiagTC
        MAX-ACCESS read-only
        STATUS     current
        DESCRIPTION
            "A diagnostic code specifying the local system's reason
             for the last transition of the session from up(4)
             to some other state."
        ::= { bfdSessEntry 12 }

    bfdSessOperMode OBJECT-TYPE
        SYNTAX     BfdSessOperModeTC
        MAX-ACCESS read-create
        STATUS     current
        DESCRIPTION
            "This object specifies current operating mode that BFD
             session is operating in."
    ::= { bfdSessEntry 13 }

    bfdSessDemandModeDesiredFlag OBJECT-TYPE
        SYNTAX     TruthValue
        MAX-ACCESS read-create
        STATUS     current
        DESCRIPTION
            "This object indicates that the local system's
             desire to use Demand mode. Specifically, it is set
             to true(1) if the local system wishes to use
             Demand mode or false(2) if not"
        DEFVAL { false }
        ::= { bfdSessEntry 14 }

    bfdSessControlPlaneIndepFlag OBJECT-TYPE
        SYNTAX     TruthValue
        MAX-ACCESS read-create
        STATUS     current
        DESCRIPTION
            "This object indicates that the local system's
             ability to continue to function through a disruption of
             the control plane. Specifically, it is set
             to true(1) if the local system BFD implementation is
             independent of the control plane. Otherwise, the
             value is set to false(2)"
        DEFVAL { false }
        ::= { bfdSessEntry 15 }

    bfdSessMultipointFlag OBJECT-TYPE
        SYNTAX     TruthValue
        MAX-ACCESS read-create
        STATUS     current
        DESCRIPTION
            "This object indicates the Multipoint (M) bit for this
             session. It is set to true(1) if Multipoint (M) bit is
             set to 1. Otherwise, the value is set to false(2)"
        DEFVAL { false }
        ::= { bfdSessEntry 16 }

    bfdSessInterface OBJECT-TYPE
        SYNTAX     InterfaceIndexOrZero
        MAX-ACCESS read-create
        STATUS     current
        DESCRIPTION
            "This object contains an interface index used to indicate
             the interface which this BFD session is running on. This
             value can be zero if there is no interface associated
             with this BFD session."
        ::= { bfdSessEntry 17 }

    bfdSessSrcAddrType OBJECT-TYPE
        SYNTAX     InetAddressType
        MAX-ACCESS read-create
        STATUS     current
        DESCRIPTION
            "This object specifies IP address type of the source IP
             address of this BFD session. Only values unknown(0),
             ipv4(1), ipv6(2), or ipv6z(4) have to be supported.
             The value of unknown(0) is allowed only when the session
             is singleHop(1) and the source IP address of this BFD
             session is drived from the outgoing interface, or when
             the BFD session is not associated with a specific
             interface. If any other unsupported values are attempted
             in a set operation, the agent MUST return an
             inconsistentValue error."
      ::= { bfdSessEntry 18 }

    bfdSessSrcAddr OBJECT-TYPE
        SYNTAX     InetAddress (SIZE (0|4|16|20))
        MAX-ACCESS read-create
        STATUS     current
        DESCRIPTION
            "This object specifies the source IP address of this BFD
             session."
        ::= { bfdSessEntry 19 }

    bfdSessDstAddrType OBJECT-TYPE
        SYNTAX     InetAddressType
        MAX-ACCESS read-create
        STATUS     current
        DESCRIPTION
            "This object specifies IP address type of the neighboring IP
             address which is being monitored with this BFD session.
             Only values unknown(0), ipv4(1), ipv6(2), or ipv6z(4)
             have to be supported. The value of unknown(0) is allowed
             only when the session is singleHop(1) and the outgoing
             interface is of type point-to-point, or when the BFD
             session is not associated with a specific interface. If  
             any other unsupported values are attempted in a set   
             operation, the agent MUST return an inconsistentValue   
             error."
      ::= { bfdSessEntry 20 }

    bfdSessDstAddr OBJECT-TYPE
        SYNTAX     InetAddress (SIZE (0|4|16|20))
        MAX-ACCESS read-create
        STATUS     current
        DESCRIPTION
            "This object specifies the neighboring IP address which is

             being monitored with this BFD session."
        ::= { bfdSessEntry 21 }

    bfdSessGTSM OBJECT-TYPE
        SYNTAX  TruthValue
        MAX-ACCESS read-create
        STATUS current
        DESCRIPTION
           "Setting the value of this object to true(1) will enable   
            GTSM protection of the BFD session.  GTSM MUST be enabled   
            on a singleHop(1) session if no authentication is in use."
        REFERENCE
           "RFC5082, The Generalized TTL Security Mechanism (GTSM).
            RFC5881, Section 5"
        DEFVAL { false }
        ::= { bfdSessEntry 22 }

    bfdSessGTSMTTL OBJECT-TYPE
        SYNTAX Unsigned32 (0..255)
        MAX-ACCESS read-create
        STATUS current
        DESCRIPTION
            "This object is valid only when bfdSessGTSM protection is
             enabled on the system. This object specifies the minimum
             allowed TTL for received BFD control packets. For
             singleHop(1) session, if GTSM protection is enabled,
             this object SHOULD be set to maximum TTL allowed for
             single hop. The value of zero(0) indicates that
             bfdSessGTSM is disabled."
        REFERENCE
           "RFC5082, The Generalized TTL Security Mechanism (GTSM).
            RFC5881, Section 5"
        DEFVAL { 0 }
        ::= { bfdSessEntry 23 }

    bfdSessDesiredMinTxInterval OBJECT-TYPE
        SYNTAX     BfdIntervalTC
        MAX-ACCESS read-create
        STATUS     current
        DESCRIPTION
            "This object specifies the minimum interval, in
             microseconds, that the local system would like to use
             when transmitting BFD Control packets. The value of
             zero(0) is reserved, and should not be used."
        REFERENCE
            "RFC5880, Section 4.1"
        ::= { bfdSessEntry 24 }

    bfdSessReqMinRxInterval OBJECT-TYPE
       SYNTAX     BfdIntervalTC
        MAX-ACCESS read-create
        STATUS     current
        DESCRIPTION
            "This object specifies the minimum interval, in
             microseconds, between received BFD Control packets the
             local system is capable of supporting. The value of
             zero(0) can be specified when the transmitting system
             does not want the remote system to send any periodic BFD
             control packets."
        REFERENCE
            "RFC5880, Section 4.1"
        ::= { bfdSessEntry 25 }

    bfdSessReqMinEchoRxInterval OBJECT-TYPE
        SYNTAX     BfdIntervalTC
        MAX-ACCESS read-create
        STATUS     current
        DESCRIPTION
            "This object specifies the minimum interval, in
             microseconds, between received BFD Echo packets that this
             system is capable of supporting. Value must be zero(0) if
             this is a multihop BFD session."
        ::= { bfdSessEntry 26 }

    bfdSessDetectMult OBJECT-TYPE
        SYNTAX     BfdMultiplierTC
        MAX-ACCESS read-create
        STATUS     current
        DESCRIPTION
            "This object specifies the Detect time multiplier."
        ::= { bfdSessEntry 27 }

    bfdSessNegotiatedInterval OBJECT-TYPE
        SYNTAX     BfdIntervalTC
        MAX-ACCESS read-only
        STATUS     current
        DESCRIPTION
            "This object specifies the negotiated interval, in
             microseconds, that the local system is transmitting
             BFD Control packets."
        ::= { bfdSessEntry 28 }

    bfdSessNegotiatedEchoInterval OBJECT-TYPE
        SYNTAX     BfdIntervalTC
        MAX-ACCESS read-only
        STATUS     current
        DESCRIPTION
            "This object specifies the negotiated interval, in
             microseconds, that the local system is transmitting
             BFD echo packets. Value is expected to be zero if
             the sessions is not running in echo mode."
        ::= { bfdSessEntry 29 }

    bfdSessNegotiatedDetectMult OBJECT-TYPE
        SYNTAX     BfdMultiplierTC
        MAX-ACCESS read-only
        STATUS     current
        DESCRIPTION
            "This object specifies the Detect time multiplier."
        ::= { bfdSessEntry 30 }

    bfdSessAuthPresFlag OBJECT-TYPE
        SYNTAX     TruthValue
        MAX-ACCESS read-create
        STATUS     current
        DESCRIPTION
            "This object indicates that the local system's
             desire to use Authentication. Specifically, it is set
             to true(1) if the local system wishes the session
             to be authenticated or false(2) if not."
        REFERENCE
            "RFC5880, Sections 4.2 - 4.4"
        DEFVAL { false }
        ::= { bfdSessEntry 31 }

    bfdSessAuthenticationType OBJECT-TYPE
        SYNTAX     BfdSessAuthenticationTypeTC
        MAX-ACCESS read-create
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping. Value -1
             indicates that no authentication is in use for this
             session."
        REFERENCE
            "RFC5880, Sections 4.2 - 4.4"
        DEFVAL { -1 }
        ::= { bfdSessEntry 32 }

    bfdSessAuthenticationKeyID OBJECT-TYPE
        SYNTAX     Integer32 (-1 | 0..255)
        MAX-ACCESS read-create
        STATUS     current
        DESCRIPTION
            "The authentication key ID in use for this session.  This
             object permits multiple keys to be active simultaneously.
             When bfdSessAuthPresFlag is false(2), then the value
             of this object MUST be -1.  The value -1 indicates that
             no Authentication Key ID will be present in the optional
             BFD Authentication Section."
        REFERENCE
            "RFC5880, Sections 4.2 - 4.4"
        DEFVAL { -1 }
        ::= { bfdSessEntry 33 }

    bfdSessAuthenticationKey OBJECT-TYPE
        SYNTAX     BfdSessionAuthenticationKeyTC
        MAX-ACCESS read-create
        STATUS     current
        DESCRIPTION
            "The authentication key.  When the
             bfdSessAuthenticationType is simplePassword(1), the value
             of this object is the password present in the BFD packets.

             When the bfdSessAuthentication type is one of the keyed
             authentication types, this value is used in the
             computation of the key present in the BFD authentication
             packet."
        REFERENCE
            "RFC5880, Sections 4.2 - 4.4"
        ::= { bfdSessEntry 34 }

    bfdSessStorType OBJECT-TYPE
        SYNTAX     StorageType
        MAX-ACCESS read-create
        STATUS     current
        DESCRIPTION
            "This variable indicates the storage type for this
             object. Conceptual rows having the value
             'permanent' need not allow write-access to any
             columnar objects in the row."
        ::= { bfdSessEntry 35 }

    bfdSessRowStatus OBJECT-TYPE
        SYNTAX     RowStatus
        MAX-ACCESS read-create
        STATUS     current
        DESCRIPTION
            "This variable is used to create, modify, and/or
             delete a row in this table. When a row in this
             table has a row in the active(1) state, no
             objects in this row can be modified except the
             bfdSessRowStatus and bfdSessStorageType."
        ::= { bfdSessEntry 36 }

 -- BFD Session Performance Table

    bfdSessPerfTable OBJECT-TYPE
        SYNTAX     SEQUENCE OF BfdSessPerfEntry
        MAX-ACCESS not-accessible
        STATUS     current
        DESCRIPTION
            "This table specifies BFD Session performance counters."
        ::= { bfdObjects 3 }

    bfdSessPerfEntry OBJECT-TYPE
        SYNTAX     BfdSessPerfEntry
        MAX-ACCESS not-accessible
        STATUS     current
        DESCRIPTION
            "An entry in this table is created by a BFD-enabled node
             for every BFD Session. bfdSessPerfDiscTime is used to
             indicate potential discontinuity for all counter objects
             in this table."
        AUGMENTS    { bfdSessEntry }
        ::= { bfdSessPerfTable 1 }

    BfdSessPerfEntry ::= SEQUENCE {
       bfdSessPerfCtrlPktIn           Counter32,
       bfdSessPerfCtrlPktOut          Counter32,
       bfdSessPerfCtrlPktDrop         Counter32,
       bfdSessPerfCtrlPktDropLastTime TimeStamp,
       bfdSessPerfEchoPktIn           Counter32,
       bfdSessPerfEchoPktOut          Counter32,
       bfdSessPerfEchoPktDrop         Counter32,
       bfdSessPerfEchoPktDropLastTime TimeStamp,
       bfdSessUpTime                  TimeStamp,
       bfdSessPerfLastSessDownTime    TimeStamp,
       bfdSessPerfLastCommLostDiag    BfdDiagTC,
       bfdSessPerfSessUpCount         Counter32,
       bfdSessPerfDiscTime            TimeStamp,

       -- High Capacity Counters
       bfdSessPerfCtrlPktInHC         Counter64,
       bfdSessPerfCtrlPktOutHC        Counter64,
       bfdSessPerfCtrlPktDropHC       Counter64,
       bfdSessPerfEchoPktInHC         Counter64,
       bfdSessPerfEchoPktOutHC        Counter64,

       bfdSessPerfEchoPktDropHC       Counter64
    }

 -- Ed Note: should we add per-diag code counts here,

    bfdSessPerfCtrlPktIn OBJECT-TYPE
        SYNTAX     Counter32
        MAX-ACCESS read-only
        STATUS     current
        DESCRIPTION
            "The total number of BFD control messages received for this
             BFD session. This value MUST be equal to the least
             significant 32 bits of bfdSessPerfCtrlPktInHC."
        ::= { bfdSessPerfEntry 1 }

    bfdSessPerfCtrlPktOut OBJECT-TYPE
        SYNTAX     Counter32
        MAX-ACCESS read-only
        STATUS     current
        DESCRIPTION
            "The total number of BFD control messages sent for this BFD
             session. This value MUST be equal to the least significant
             32 bits of bfdSessPerfCtrlPktOutHC."
        ::= { bfdSessPerfEntry 2 }

    bfdSessPerfCtrlPktDrop OBJECT-TYPE
        SYNTAX     Counter32
        MAX-ACCESS read-only
        STATUS     current
        DESCRIPTION
            "The total number of BFD control messages received for this
             session yet dropped for being invalid. This value MUST be
             equal to the least significant 32 bits of
             bfdSessPerfCtrlPktDropHC."
        ::= { bfdSessPerfEntry 3 }

    bfdSessPerfCtrlPktDropLastTime OBJECT-TYPE
        SYNTAX     TimeStamp
        MAX-ACCESS read-only
        STATUS     current
        DESCRIPTION
            "The value of sysUpTime on the most recent occasion at
             which received BFD control message for this session was
             dropped. If no such up event exists, this object contains
             a zero value."
        ::= { bfdSessPerfEntry 4 }

    bfdSessPerfEchoPktIn OBJECT-TYPE
        SYNTAX     Counter32
      MAX-ACCESS read-only
        STATUS     current
        DESCRIPTION
            "The total number of BFD echo messages received for this
             BFD session. This value MUST be equal to the least
             significant 32 bits of bfdSessPerfEchoPktInHC."
        ::= { bfdSessPerfEntry 5 }

    bfdSessPerfEchoPktOut OBJECT-TYPE
        SYNTAX     Counter32
        MAX-ACCESS read-only
        STATUS     current
        DESCRIPTION
            "The total number of BFD echo messages sent for this BFD
             session. This value MUST be equal to the least significant
             32 bits of bfdSessPerfEchoPktOutHC."
        ::= { bfdSessPerfEntry 6 }

    bfdSessPerfEchoPktDrop OBJECT-TYPE
        SYNTAX     Counter32
        MAX-ACCESS read-only
        STATUS     current
        DESCRIPTION
            "The total number of BFD echo messages received for this
             session yet dropped for being invalid. This value MUST be
             equal to the least significant 32 bits of
             bfdSessPerfEchoPktDropHC."
        ::= { bfdSessPerfEntry 7 }

    bfdSessPerfEchoPktDropLastTime OBJECT-TYPE
        SYNTAX     TimeStamp
        MAX-ACCESS read-only
        STATUS     current
        DESCRIPTION
            "The value of sysUpTime on the most recent occasion at
             which received BFD echo message for this session was
             dropped. If no such up event exists, this object contains
             a zero value."
        ::= { bfdSessPerfEntry 8 }

    bfdSessUpTime OBJECT-TYPE
        SYNTAX     TimeStamp
        MAX-ACCESS read-only
        STATUS     current
        DESCRIPTION
            "The value of sysUpTime on the most recent occasion at  
             which the session came up. If no such up event exists this
             object contains a zero value."
        ::= { bfdSessPerfEntry 9 }

    bfdSessPerfLastSessDownTime OBJECT-TYPE
        SYNTAX     TimeStamp
        MAX-ACCESS read-only
        STATUS     current
        DESCRIPTION
            "The value of sysUpTime on the most recent occasion at
             which the last time communication was lost with the
             neighbor. If no such down event exist this object
             contains a zero value."
        ::= { bfdSessPerfEntry 10 }

    bfdSessPerfLastCommLostDiag OBJECT-TYPE
        SYNTAX     BfdDiagTC
        MAX-ACCESS read-only
        STATUS     current
        DESCRIPTION
            "The BFD diag code for the last time communication was lost
             with the neighbor. If no such down event exists this object
             contains a zero value."
        ::= { bfdSessPerfEntry 11 }

    bfdSessPerfSessUpCount OBJECT-TYPE
        SYNTAX     Counter32
        MAX-ACCESS read-only
        STATUS     current
        DESCRIPTION
            "The number of times this session has gone into the Up
             state since the system last rebooted."
        ::= { bfdSessPerfEntry 12 }

    bfdSessPerfDiscTime OBJECT-TYPE
        SYNTAX     TimeStamp
        MAX-ACCESS read-only
        STATUS     current
        DESCRIPTION
          "The value of sysUpTime on the most recent occasion at
           which any one or more of the session counters suffered
           a discontinuity.
           The relevant counters are the specific instances associated
           with this BFD session of any Counter32 object contained in
           the BfdSessPerfTable. If no such discontinuities have
           occurred since the last re-initialization of the local
           management subsystem, then this object contains a zero
           value."
        ::= { bfdSessPerfEntry 13 }

    bfdSessPerfCtrlPktInHC OBJECT-TYPE
        SYNTAX     Counter64
        MAX-ACCESS read-only
        STATUS     current
        DESCRIPTION
            "This value represents the total number of BFD control
             messages received for this BFD session."
        ::= { bfdSessPerfEntry 14 }

    bfdSessPerfCtrlPktOutHC OBJECT-TYPE
        SYNTAX     Counter64
        MAX-ACCESS read-only
        STATUS     current
        DESCRIPTION
            "This value represents the total number of BFD control
             messages transmitted for this BFD session."
        ::= { bfdSessPerfEntry 15 }

    bfdSessPerfCtrlPktDropHC OBJECT-TYPE
        SYNTAX     Counter64
        MAX-ACCESS read-only
        STATUS     current
        DESCRIPTION
            "This value represents the total number of BFD control
             messages received for this BFD session yet dropped for
             being invalid."
        ::= { bfdSessPerfEntry 16 }

    bfdSessPerfEchoPktInHC OBJECT-TYPE
        SYNTAX     Counter64
        MAX-ACCESS read-only
        STATUS     current
        DESCRIPTION
            "This value represents the total number of BFD echo
             messages received for this BFD session."
        ::= { bfdSessPerfEntry 17 }

    bfdSessPerfEchoPktOutHC OBJECT-TYPE
        SYNTAX     Counter64
        MAX-ACCESS read-only
        STATUS     current
        DESCRIPTION
            "This value represents the total number of BFD echo
             messages transmitted for this BFD session."
        ::= { bfdSessPerfEntry 18 }

    bfdSessPerfEchoPktDropHC OBJECT-TYPE
        SYNTAX     Counter64
        MAX-ACCESS read-only
        STATUS     current
        DESCRIPTION
           "This value represents the total number of BFD echo
             messages received for this BFD session yet dropped
             for being invalid."
        ::= { bfdSessPerfEntry 19 }

 -- BFD Session Discriminator Mapping Table

    bfdSessDiscMapTable OBJECT-TYPE
        SYNTAX     SEQUENCE OF BfdSessDiscMapEntry
        MAX-ACCESS not-accessible
        STATUS     current
        DESCRIPTION
            "The BFD Session Discriminator Mapping Table maps a
             local discriminator value to associated BFD session's
             BfdSessIndexTC used in the bfdSessionTable."
        ::= { bfdObjects 4 }

    bfdSessDiscMapEntry OBJECT-TYPE
        SYNTAX     BfdSessDiscMapEntry
        MAX-ACCESS not-accessible
        STATUS     current
        DESCRIPTION
            "The BFD Session Discriminator Map Entry describes
             BFD session that is mapped to this BfdSessIndexTC."
        INDEX { bfdSessDiscriminator }
        ::= { bfdSessDiscMapTable 1 }

    BfdSessDiscMapEntry ::= SEQUENCE {
        bfdSessDiscMapIndex            BfdSessIndexTC
    }

    bfdSessDiscMapIndex OBJECT-TYPE
        SYNTAX     BfdSessIndexTC
        MAX-ACCESS read-only
        STATUS     current
        DESCRIPTION
            "This object specifies the BfdSessIndexTC referred to by
             the indices of this row. In essence, a mapping is
             provided between these indexes and the BfdSessTable."
        ::= { bfdSessDiscMapEntry 1 }

 -- BFD Session IP Mapping Table

    bfdSessIpMapTable OBJECT-TYPE
        SYNTAX     SEQUENCE OF BfdSessIpMapEntry
        MAX-ACCESS not-accessible
        STATUS     current
        DESCRIPTION
            "The BFD Session IP Mapping Table maps given
            bfdSessInterface, bfdSessSrcAddrType, bfdSessSrcAddr,
             bfdSessDstAddrType and bfdSessDstAddr
             to an associated BFD session's BfdSessIndexTC used in
             the bfdSessionTable."
        ::= { bfdObjects 5 }

    bfdSessIpMapEntry OBJECT-TYPE
        SYNTAX     BfdSessIpMapEntry
        MAX-ACCESS not-accessible
        STATUS     current
        DESCRIPTION
           "The BFD Session IP Map Entry describes
            BFD session that is mapped to this BfdSessIndexTC."
        INDEX {
            bfdSessInterface,
            bfdSessSrcAddrType,
            bfdSessSrcAddr,
            bfdSessDstAddrType,
            bfdSessDstAddr
        }
        ::= { bfdSessIpMapTable 1 }

    BfdSessIpMapEntry ::= SEQUENCE {
        bfdSessIpMapIndex            BfdSessIndexTC
    }

    bfdSessIpMapIndex OBJECT-TYPE
        SYNTAX     BfdSessIndexTC
        MAX-ACCESS read-only
        STATUS     current
        DESCRIPTION
            "This object specifies the BfdSessIndexTC referred to by
             the indexes of this row. In essence, a mapping is
             provided between these indexes and the BfdSessTable."
        ::= { bfdSessIpMapEntry 1 }

 -- Notification Configuration

    bfdSessUp NOTIFICATION-TYPE
        OBJECTS {
            bfdSessDiag, -- low range value
            bfdSessDiag  -- high range value
        }
        STATUS     current
        DESCRIPTION
            "This notification is generated when the
             bfdSessState object for one or more contiguous
             entries in bfdSessTable are about to enter the up(4)
             state from some other state. The included values of

             bfdSessDiag MUST both be set equal to this
             new state (i.e: up(4)).  The two instances of
             bfdSessDiag in this notification indicate the range
             of indexes that are affected.  Note that all the indexes
             of the two ends of the range can be derived from the
             instance identifiers of these two objects.  For the
             cases where a contiguous range of sessions
             have transitioned into the up(4) state at roughly
             the same time, the device SHOULD issue a single
             notification for each range of contiguous indexes in
             an effort to minimize the emission of a large number
             of notifications.  If a notification has to be
             issued for just a single bfdSessEntry, then
             the instance identifier (and values) of the two
             bfdSessDiag objects MUST be the identical."
        ::= { bfdNotifications 1 }

    bfdSessDown NOTIFICATION-TYPE
        OBJECTS {
            bfdSessDiag, -- low range value
            bfdSessDiag  -- high range value
        }
        STATUS     current
        DESCRIPTION
            "This notification is generated when the
             bfdSessState object for one or more contiguous
             entries in bfdSessTable are about to enter the down(2)
             or adminDown(1) states from some other state. The included
             values of bfdSessDiag MUST both be set equal to this new
             state (i.e: down(2) or adminDown(1)).  The two instances
             of bfdSessDiag in this notification indicate the range
             of indexes that are affected.  Note that all the indexes
             of the two ends of the range can be derived from the
             instance identifiers of these two objects.  For
             cases where a contiguous range of sessions
             have transitioned into the down(2) or adminDown(1) states
             at roughly the same time, the device SHOULD issue a single
             notification for each range of contiguous indexes in
             an effort to minimize the emission of a large number
             of notifications.  If a notification has to be
             issued for just a single bfdSessEntry, then
             the instance identifier (and values) of the two
             bfdSessDiag objects MUST be the identical."
        ::= { bfdNotifications 2 }

 -- Ed Note: We need to add notification for changes
 -- when the two ends automatically negotiate to a new detection time
 -- value or when detection multiplier changes.
-- Module compliance.

    bfdGroups
        OBJECT IDENTIFIER ::= { bfdConformance 1 }

    bfdCompliances
        OBJECT IDENTIFIER ::= { bfdConformance 2 }

 -- Compliance requirement for fully compliant implementations.

    bfdModuleFullCompliance MODULE-COMPLIANCE
        STATUS current
        DESCRIPTION
            "Compliance statement for agents that provide full
             support for the BFD-MIB module. Such devices can
             then be monitored and also be configured using
             this MIB module."

        MODULE -- This module.

        MANDATORY-GROUPS {
            bfdSessionGroup,
            bfdSessionReadOnlyGroup,
            bfdSessionPerfGroup,
            bfdNotificationGroup
        }

        GROUP        bfdSessionPerfHCGroup
        DESCRIPTION  "This group is mandatory for all systems that
                      are able to support the Counter64 date type."

        OBJECT       bfdSessSrcAddrType
        SYNTAX       InetAddressType { unknown(0), ipv4(1),
                                       ipv6(2), ipv6z(4) }
        DESCRIPTION  "Only unknown(0), ipv4(1), ipv6(2) and ipv6z(4)
                      support are required."

        OBJECT       bfdSessSrcAddr
        SYNTAX       InetAddress (SIZE (0|4|16|20))
        DESCRIPTION  "An implementation is only required to support
                      unknown(0), ipv4(1), ipv6(2) and ipv6z(4) sizes."

        OBJECT       bfdSessDstAddrType
        SYNTAX       InetAddressType { unknown(0), ipv4(1),
                                       ipv6(2), ipv6z(4) }
        DESCRIPTION  "Only unknown(0), ipv4(1), ipv6(2) and ipv6z(4)
                      support are required."

        OBJECT       bfdSessDstAddr
       SYNTAX       InetAddress (SIZE (0|4|16|20))
        DESCRIPTION  "An implementation is only required to support
                      unknown(0), ipv4(1), ipv6(2) and ipv6z(4) sizes."

        OBJECT       bfdSessRowStatus
        SYNTAX       RowStatus { active(1), notInService(2) }
        WRITE-SYNTAX RowStatus { active(1), notInService(2),
                                 createAndGo(4), destroy(6) }
        DESCRIPTION  "Support for createAndWait and notReady is not
                      required."

        ::= { bfdCompliances 1 }

    bfdModuleReadOnlyCompliance MODULE-COMPLIANCE
        STATUS current
        DESCRIPTION
            "Compliance requirement for implementations that only
             provide read-only support for BFD-MIB. Such devices
             can then be monitored but cannot be configured using
             this MIB module."

        MODULE -- This module.

        MANDATORY-GROUPS {
            bfdSessionGroup,
            bfdSessionReadOnlyGroup,
            bfdSessionPerfGroup,
            bfdNotificationGroup
        }

        GROUP        bfdSessionPerfHCGroup
        DESCRIPTION  "This group is mandatory for all systems that
                      are able to support the Counter64 date type."

        OBJECT       bfdSessVersionNumber
        MIN-ACCESS   read-only
        DESCRIPTION  "Write access is not required."

        OBJECT       bfdSessType
        MIN-ACCESS   read-only
        DESCRIPTION  "Write access is not required."

        OBJECT       bfdSessDestinationUdpPort
        MIN-ACCESS   read-only
        DESCRIPTION  "Write access is not required."

        OBJECT       bfdSessSourceUdpPort
        MIN-ACCESS   read-only
        DESCRIPTION  "Write access is not required."
        OBJECT       bfdSessEchoSourceUdpPort
        MIN-ACCESS   read-only
        DESCRIPTION  "Write access is not required."

        OBJECT       bfdSessAdminStatus
        MIN-ACCESS   read-only
        DESCRIPTION  "Write access is not required."

        OBJECT       bfdSessOperMode
        MIN-ACCESS   read-only
        DESCRIPTION  "Write access is not required."

        OBJECT       bfdSessDemandModeDesiredFlag
        MIN-ACCESS   read-only
        DESCRIPTION  "Write access is not required."

        OBJECT       bfdSessControlPlaneIndepFlag
        MIN-ACCESS   read-only
        DESCRIPTION  "Write access is not required."

        OBJECT       bfdSessMultipointFlag
        MIN-ACCESS   read-only
        DESCRIPTION  "Write access is not required."

        OBJECT       bfdSessInterface
        MIN-ACCESS   read-only
        DESCRIPTION  "Write access is not required."

        OBJECT       bfdSessSrcAddrType
        SYNTAX       InetAddressType { unknown(0), ipv4(1),
                                       ipv6(2), ipv6z(4) }
        MIN-ACCESS   read-only
        DESCRIPTION  "Only unknown(0), ipv4(1), ipv6(2) and ipv6z(4)
                      support are required."

        OBJECT       bfdSessSrcAddr
        SYNTAX       InetAddress (SIZE (0|4|16|20))
        MIN-ACCESS   read-only
        DESCRIPTION  "An implementation is only required to support
                      unknown(0), ipv4(1), ipv6(2) and ipv6z(4) sizes."

        OBJECT       bfdSessDstAddrType
        SYNTAX       InetAddressType { unknown(0), ipv4(1),
                                       ipv6(2), ipv6z(4) }
        MIN-ACCESS   read-only
        DESCRIPTION  "Only unknown(0), ipv4(1), ipv6(2) and ipv6z(4)
                      support are required."

        OBJECT       bfdSessDstAddr
        SYNTAX       InetAddress (SIZE (0|4|16|20))
        MIN-ACCESS   read-only
        DESCRIPTION  "An implementation is only required to support
                      unknown(0), ipv4(1), ipv6(2) and ipv6z(4) sizes."

        OBJECT       bfdSessGTSM
        MIN-ACCESS   read-only
        DESCRIPTION  "Write access is not required."

        OBJECT       bfdSessGTSMTTL
        MIN-ACCESS   read-only
        DESCRIPTION  "Write access is not required."

        OBJECT       bfdSessDesiredMinTxInterval
        MIN-ACCESS   read-only
        DESCRIPTION  "Write access is not required."

        OBJECT       bfdSessReqMinRxInterval
        MIN-ACCESS   read-only
        DESCRIPTION  "Write access is not required."

        OBJECT       bfdSessReqMinEchoRxInterval
        MIN-ACCESS   read-only
        DESCRIPTION  "Write access is not required."

        OBJECT       bfdSessDetectMult
        MIN-ACCESS   read-only
        DESCRIPTION  "Write access is not required."

        OBJECT       bfdSessAuthPresFlag
        MIN-ACCESS   read-only
        DESCRIPTION  "Write access is not required."

        OBJECT       bfdSessAuthenticationType
        MIN-ACCESS   read-only
        DESCRIPTION  "Write access is not required."

        OBJECT       bfdSessAuthenticationKeyID
        MIN-ACCESS   read-only
        DESCRIPTION  "Write access is not required."

        OBJECT       bfdSessAuthenticationKey
        MIN-ACCESS   read-only
        DESCRIPTION  "Write access is not required."

        OBJECT       bfdSessStorType
        MIN-ACCESS   read-only
        DESCRIPTION  "Write access is not required."
        OBJECT       bfdSessRowStatus
        SYNTAX       RowStatus { active(1) }
        MIN-ACCESS   read-only
        DESCRIPTION  "Write access is not required."

        ::= { bfdCompliances 2 }

 -- Units of conformance.

    bfdSessionGroup OBJECT-GROUP
        OBJECTS {
            bfdAdminStatus,
            bfdSessNotificationsEnable,
            bfdSessVersionNumber,
            bfdSessType,
            bfdSessDestinationUdpPort,
            bfdSessSourceUdpPort,
            bfdSessEchoSourceUdpPort,
            bfdSessAdminStatus,
            bfdSessOperMode,
            bfdSessDemandModeDesiredFlag,
            bfdSessControlPlaneIndepFlag,
            bfdSessMultipointFlag,
            bfdSessInterface,
            bfdSessSrcAddrType,
            bfdSessSrcAddr,
            bfdSessDstAddrType,
            bfdSessDstAddr,
            bfdSessGTSM,
            bfdSessGTSMTTL,
            bfdSessDesiredMinTxInterval,
            bfdSessReqMinRxInterval,
            bfdSessReqMinEchoRxInterval,
            bfdSessDetectMult,
            bfdSessAuthPresFlag,
            bfdSessAuthenticationType,
            bfdSessAuthenticationKeyID,
            bfdSessAuthenticationKey,
            bfdSessStorType,
            bfdSessRowStatus
        }
        STATUS     current
        DESCRIPTION
            "Collection of objects needed for BFD sessions."
        ::= { bfdGroups 1 }

    bfdSessionReadOnlyGroup OBJECT-GROUP
        OBJECTS {

            bfdSessDiscriminator,
            bfdSessRemoteDiscr,
            bfdSessState,
            bfdSessRemoteHeardFlag,
            bfdSessDiag,
            bfdSessNegotiatedInterval,
            bfdSessNegotiatedEchoInterval,
            bfdSessNegotiatedDetectMult,
            bfdSessDiscMapIndex,
            bfdSessIpMapIndex
        }
        STATUS     current
        DESCRIPTION
            "Collection of read-only objects needed for BFD sessions."
        ::= { bfdGroups 2 }

    bfdSessionPerfGroup OBJECT-GROUP
        OBJECTS {
            bfdSessPerfCtrlPktIn,
            bfdSessPerfCtrlPktOut,
            bfdSessPerfCtrlPktDrop,
            bfdSessPerfCtrlPktDropLastTime,
            bfdSessPerfEchoPktIn,
            bfdSessPerfEchoPktOut,
            bfdSessPerfEchoPktDrop,
            bfdSessPerfEchoPktDropLastTime,
            bfdSessUpTime,
            bfdSessPerfLastSessDownTime,
            bfdSessPerfLastCommLostDiag,
            bfdSessPerfSessUpCount,
            bfdSessPerfDiscTime
        }
        STATUS     current
        DESCRIPTION
            "Collection of objects needed to monitor the
             performance of BFD sessions."
        ::= { bfdGroups 3 }

    bfdSessionPerfHCGroup OBJECT-GROUP
        OBJECTS {
            bfdSessPerfCtrlPktInHC,
            bfdSessPerfCtrlPktOutHC,
            bfdSessPerfCtrlPktDropHC,
            bfdSessPerfEchoPktInHC,
            bfdSessPerfEchoPktOutHC,
            bfdSessPerfEchoPktDropHC
        }
        STATUS     current
        DESCRIPTION

            "Collection of objects needed to monitor the
             performance of BFD sessions for which the
             values of bfdSessPerfPktIn, bfdSessPerfPktOut
             wrap around too quickly."
        ::= { bfdGroups 4 }

    bfdNotificationGroup NOTIFICATION-GROUP
        NOTIFICATIONS {
            bfdSessUp,
            bfdSessDown
        }
        STATUS     current
        DESCRIPTION
            "Set of notifications implemented in this
             module."
        ::= { bfdGroups 5 }

    END
