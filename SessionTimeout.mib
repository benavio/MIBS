-- -----------------------------------------------------------------------------
-- MIB NAME : Session Timeout Common mib
-- FILE NAME: SessionTimeout.mib
-- DATE     : 2017/08/14
-- VERSION  : 1.00
-- PURPOSE  : To construct the MIB structure of Session Timeout 
--            for proprietary enterprise
-- -----------------------------------------------------------------------------
-- MODIFICTION HISTORY:
-- -----------------------------------------------------------------------------
-- Version, Date, Author
-- Description:
-- [New Object]
-- [Modification]
-- Notes: (Requested by who and which project)
-- 
-- Version 1.00, 2017/08/14, Jean Chen
-- This is the first formal version for universal MIB definition.
-- -----------------------------------------------------------------------------  

SESSION-TIMEOUT-MIB DEFINITIONS ::= BEGIN

	IMPORTS
	    MODULE-IDENTITY,OBJECT-TYPE     FROM SNMPv2-SMI
	    dlink-common-mgmt               FROM DLINK-ID-REC-MIB;

	swSessionTimeoutMIB MODULE-IDENTITY
	    LAST-UPDATED "1708140000Z"
	    ORGANIZATION "D-Link Corp."
	    CONTACT-INFO
	        "http://support.dlink.com"
	    DESCRIPTION
	        "The Session Timeout module MIB for the proprietary enterprise."
	    ::= { dlink-common-mgmt 121}

	swSessionTimeoutConsole OBJECT-TYPE
	    SYNTAX      INTEGER(0..1439)   
	    UNITS       "minutes"
	    MAX-ACCESS  read-write
	    STATUS      current
	    DESCRIPTION
	        "This object indicates the timeout for auto-logout for sessions established by console.
	        Zero is a special value which means Never Timeout."
	        DEFVAL      { 0 }
	    ::= { swSessionTimeoutMIB 1 }      	

	swSessionTimeoutTelnet OBJECT-TYPE
	    SYNTAX      INTEGER(0..1439)   
	    UNITS       "minutes"
	    MAX-ACCESS  read-write
	    STATUS      current
	    DESCRIPTION
	        "This object indicates the timeout for auto-logout for sessions established by telnet.
	        Zero is a special value which means Never Timeout."
	        DEFVAL      { 0 }
	    ::= { swSessionTimeoutMIB 2 }  

 	swSessionTimeoutSSH OBJECT-TYPE
	    SYNTAX      INTEGER(0..1439)   
	    UNITS       "minutes"
	    MAX-ACCESS  read-write
	    STATUS      current
	    DESCRIPTION
	        "This object indicates the timeout for auto-logout for sessions established by SSH.
	        Zero is a special value which means Never Timeout."
	        DEFVAL      { 0 }
	    ::= { swSessionTimeoutMIB 3 }

	swOutgoingSessionTimeoutConsole OBJECT-TYPE
	    SYNTAX      INTEGER(0..1439)   
	    UNITS       "minutes"
	    MAX-ACCESS  read-write
	    STATUS      current
	    DESCRIPTION
	            "This object indicates the timeout for closing sessions established for login into another device via console.
	            Zero is a special value which means Never Timeout."
	            DEFVAL      { 0 }
	        ::= { swSessionTimeoutMIB 4 }      	

	swOutgoingSessionTimeoutTelnet OBJECT-TYPE
	    SYNTAX      INTEGER(0..1439)   
	    UNITS       "minutes"
	    MAX-ACCESS  read-write
	    STATUS      current
	    DESCRIPTION
	        "This object indicates the timeout for closing sessions established for login into another device via telnet.
	        Zero is a special value which means Never Timeout."
	        DEFVAL      { 0 }
	    ::= { swSessionTimeoutMIB 5 }  

 	swOutgoingSessionTimeoutSSH OBJECT-TYPE
	    SYNTAX      INTEGER(0..1439)   
	    UNITS       "minutes"
	    MAX-ACCESS  read-write
	    STATUS      current
	    DESCRIPTION
	        "This object indicates the timeout for closing sessions established for login into another device via SSH.
	        Zero is a special value which means Never Timeout."
	        DEFVAL      { 0 }
	    ::= { swSessionTimeoutMIB 6 }

 	swSessionTimeoutWeb OBJECT-TYPE
	    SYNTAX      INTEGER(0..1439)   
	    UNITS       "minutes"
	    MAX-ACCESS  read-write
	    STATUS      current
	    DESCRIPTION
	        "This object indicates the timeout for auto-logout for sessions established by Web.
	        Zero is a special value which means Never Timeout."
	        DEFVAL      { 0 }
	    ::= { swSessionTimeoutMIB 7 }

END
