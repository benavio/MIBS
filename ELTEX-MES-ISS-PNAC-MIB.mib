ELTEX-MES-ISS-PNAC-MIB DEFINITIONS ::= BEGIN

IMPORTS
    MODULE-IDENTITY, OBJECT-TYPE
        FROM SNMPv2-SMI
    VlanId
        FROM Q-BRIDGE-MIB
    eltMesIss
        FROM ELTEX-MES-ISS-MIB
    dot1xAuthConfigEntry
        FROM IEEE8021-PAE-MIB
    fsPnacAuthSessionEntry
        FROM ARICENT-PNAC-MIB;

eltMesIssPnacMIB MODULE-IDENTITY
    LAST-UPDATED "202406140000Z"
    ORGANIZATION "Eltex Enterprise, Ltd."
    CONTACT-INFO
            "eltex-co.ru"
    DESCRIPTION
            "Eltex MIB extensions for PNAC."
    REVISION "202406140000Z"
    DESCRIPTION
            "Added extensions for PNAC authorization mode."
    REVISION "202208290000Z"
    DESCRIPTION
            "Added eltPnacAuthSessionCurrentVlanId object."
    REVISION "202206200000Z"
    DESCRIPTION
            "Supported RADIUS attribute VLAN ID."
    REVISION "202205040000Z"
    DESCRIPTION "Initial revision."
    ::= { eltMesIss 31 }

-- -----------------------------------------------------------------------------
-- Top level MIB structure
-- -----------------------------------------------------------------------------

eltMesIssPnacObjects OBJECT IDENTIFIER ::= { eltMesIssPnacMIB 1 }

-- -----------------------------------------------------------------------------
-- MIB Groups
-- -----------------------------------------------------------------------------

eltMesIssDot1xGlobals     OBJECT IDENTIFIER ::= { eltMesIssPnacObjects 1 }
eltMesIssDot1xPortConfig  OBJECT IDENTIFIER ::= { eltMesIssPnacObjects 2 }
eltMesIssDot1xAuthSession OBJECT IDENTIFIER ::= { eltMesIssPnacObjects 3 }

-- -----------------------------------------------------------------------------
-- Pnac Table extension
-- -----------------------------------------------------------------------------

-- Authenticator Configuration Table --

eltMesIssDot1xAuthConfigTable OBJECT-TYPE
    SYNTAX SEQUENCE OF EltMesIssDot1xAuthConfigEntry
    MAX-ACCESS not-accessible
    STATUS current
    DESCRIPTION
        "This table augments the dot1xAuthConfigTable table."
    ::= { eltMesIssDot1xPortConfig 1 }

eltMesIssDot1xAuthConfigEntry OBJECT-TYPE
    SYNTAX EltMesIssDot1xAuthConfigEntry
    MAX-ACCESS not-accessible
    STATUS current
    DESCRIPTION
        "The configuration information for dot1x.
         An entry appears in this table for each physical interface."
    AUGMENTS { dot1xAuthConfigEntry }
    ::= { eltMesIssDot1xAuthConfigTable 1 }

EltMesIssDot1xAuthConfigEntry ::= SEQUENCE {
    eltMesIssDot1xGuestVlanId               VlanId,
    eltMesIssDot1xUnauthenticatedVlanId     VlanId,
    eltMesIssDot1xRadiusAttrVlanIdAction    INTEGER(1..3),
    eltMesIssDot1xExtAuthMode               BITS
}

eltMesIssDot1xGuestVlanId OBJECT-TYPE
    SYNTAX VlanId
    MAX-ACCESS read-write
    STATUS current
    DESCRIPTION
        "This field contains the guest VLAN ID, default value means no setting."
    DEFVAL { 0 }
    ::=  { eltMesIssDot1xAuthConfigEntry 1 }

eltMesIssDot1xUnauthenticatedVlanId OBJECT-TYPE
    SYNTAX VlanId
    MAX-ACCESS read-write
    STATUS current
    DESCRIPTION
        "This field contains the unauthenticated VLAN ID, default value means no setting."
    DEFVAL { 0 }
    ::=  { eltMesIssDot1xAuthConfigEntry 2 }

eltMesIssDot1xRadiusAttrVlanIdAction OBJECT-TYPE
    SYNTAX  INTEGER {
        ignore(1),
        mandatory(2),
        optional(3)
    }
    MAX-ACCESS read-write
    STATUS current
    DESCRIPTION
        "This field controls treatment of VLAN ID that is received
         from Radius attributes in Radius-Accept message.
         ignore(1) - VLAN ID attribute is ignored.
         mandatory(2) - VLAN ID attribute is required for authorization.
         optional(3) - VLAN ID attribute is used if present."
    DEFVAL { ignore }
    ::=  { eltMesIssDot1xAuthConfigEntry 3 }

eltMesIssDot1xExtAuthMode OBJECT-TYPE
    SYNTAX BITS {
        dot1x (0),
        mac (1)
    }
    MAX-ACCESS read-write
    STATUS current
    DESCRIPTION
        "This object determines which type of authorization will be used on the port."
    ::= { eltMesIssDot1xAuthConfigEntry 4 }

-- Authenticator Session Table --

eltPnacAuthSessionTable OBJECT-TYPE
    SYNTAX      SEQUENCE OF EltPnacAuthSessionEntry
    MAX-ACCESS  not-accessible
    STATUS      current
    DESCRIPTION
        "This table augments the fsPnacAuthSessionTable table."
    ::= { eltMesIssDot1xAuthSession 1 }

eltPnacAuthSessionEntry OBJECT-TYPE
    SYNTAX      EltPnacAuthSessionEntry
    MAX-ACCESS  not-accessible
    STATUS      current
    DESCRIPTION
        "This entry contains authentication session information
         associated with each supplicant while authenticator
         operates in MAC based authentication mode."
    AUGMENTS { fsPnacAuthSessionEntry }
    ::= { eltPnacAuthSessionTable 1 }

EltPnacAuthSessionEntry ::=  SEQUENCE {
    eltPnacAuthSessionCurrentVlanId VlanId
}

eltPnacAuthSessionCurrentVlanId OBJECT-TYPE
    SYNTAX      VlanId
    MAX-ACCESS  read-only
    STATUS      current
    DESCRIPTION
        "This field contains the value of the client's current VLAN ID."
   ::= { eltPnacAuthSessionEntry 1 }

END
