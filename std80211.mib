-- /*****************************************************************
-- Copyright (C) 2013 Aricent Group . All Rights Reserved
-- /*****************************************************************
--  *                                                               *
--  * - $Id: std80211.mib,                                          *
--  *                                                               *
--  * This file explains the proprietary MIB implemented for std802 *
--  ****************************************************************/

-- **********************************************************************
-- * IEEE 802.11 MIB
-- **********************************************************************
IEEE802dot11-MIB DEFINITIONS ::= BEGIN
IMPORTS
MODULE-IDENTITY, OBJECT-TYPE, NOTIFICATION-TYPE,
Integer32, Counter32, Counter64, Unsigned32, TimeTicks, Gauge32
FROM SNMPv2-SMI
DisplayString , MacAddress, RowStatus, TruthValue,
TEXTUAL-CONVENTION FROM SNMPv2-TC
MODULE-COMPLIANCE, OBJECT-GROUP, NOTIFICATION-GROUP FROM SNMPv2-CONF
ifIndex, InterfaceIndex FROM IF-MIB;
-- **********************************************************************
-- * MODULE IDENTITY
-- **********************************************************************
ieee802dot11 MODULE-IDENTITY
LAST-UPDATED "201203300000Z"
ORGANIZATION "IEEE 802.11"
CONTACT-INFO
"Chair: Bruce Kraemer
Postal: 517 La Costa Court
Melbourne, FL 32940, USA
Tel: +1 321 427 4098
Fax: +1 321 751 3988
E-mail: bkraemer@ieee.org
Editor: Adrian P Stephens
E-mail: adrian.p.stephens@ieee.org"
DESCRIPTION
"The MIB module for IEEE 802.11 entities.
iso(1).member-body(2).us(840).ieee802dot11(10036)"
REVISION "201203300000Z"
DESCRIPTION "Draft Revision MB of the 802.11 Standard.
Note that not all objects within this MIB are referenced by a group, and
not all groups are referenced by a MODULE-COMPLIANCE statement. Some
existing groups and the dot11Compliance MODULE-COMPLIANCE have been modified
since the previous revision of this standard.
Implementations should not claim compliance to dot11Compliance."
--::= { us 10036 }
::= { 1 2 840 10036 }
-- **********************************************************************
-- * Tree Definition
-- **********************************************************************
--member-body OBJECT IDENTIFIER ::= { iso 2 }
--us OBJECT IDENTIFIER ::= { member-body 840 }
-- **********************************************************************
-- * Major sections
-- **********************************************************************
-- Station ManagemenT (SMT) Attributes
-- DEFINED AS "The SMT object class provides the necessary support
-- at the station to manage the processes in the station such that
-- the station may work cooperatively as a part of an IEEE 802.11
-- network."
dot11smt OBJECT IDENTIFIER ::= { ieee802dot11 1 }
-- dot11smt GROUPS
-- dot11StationConfigTable ::= { dot11smt 1 }
-- dot11AuthenticationAlgorithmsTable ::= { dot11smt 2 }
-- dot11WEPDefaultKeysTable ::= { dot11smt 3 }
-- dot11WEPKeyMappingsTable ::= { dot11smt 4 }
-- dot11PrivacyTable ::= { dot11smt 5 }
-- dot11SMTnotification ::= { dot11smt 6 }
-- dot11MultiDomainCapabilityTable ::= { dot11smt 7 }
-- dot11SpectrumManagementTable ::= { dot11smt 8 }
-- dot11RSNAConfigTable ::= { dot11smt 9 }
-- dot11RSNAConfigPairwiseCiphersTable ::= { dot11smt 10 }
-- dot11RSNAConfigAuthenticationSuitesTable ::= { dot11smt 11 }
-- dot11RSNAStatsTable ::= { dot11smt 12 }
-- dot11OperatingClassesTable ::= { dot11smt 13 }
-- dot11RadioMeasurement ::= { dot11smt 14 }
-- dot11FastBSSTransitionConfigTable ::= { dot11smt 15 }
-- dot11LCIDSETable ::= { dot11smt 16 }
-- dot11HTStationConfigTable ::= { dot11smt 17 }
-- dot11WirelessMgmtOptionsTable ::= { dot11smt 18}
-- dot11LocationServicesNextIndex ::= { dot11smt 19}
-- dot11LocationServicesTable ::= { dot11smt 20}
-- dot11WirelessMGTEventTable ::= { dot11smt 21}
-- dot11WirelessNetworkManagement ::= { dot11smt 22}
-- dot11MeshSTAConfigTable ::= { dot11smt 23 }
-- dot11MeshHWMPConfigTable ::= { dot11smt 24 }
-- dot11RSNAConfigPasswordValueTable ::= { dot11smt 25 }
-- dot11RSNAConfigDLCGroupTable ::= { dot11smt 26 }
-- MAC Attributes
-- DEFINED AS "The MAC object class provides the necessary support
-- for the access control, generation, and verification of frame
-- check sequences (FCSs), and proper delivery of valid data to
-- upper layers."
dot11mac OBJECT IDENTIFIER ::= { ieee802dot11 2 }
-- MAC GROUPS
-- dot11OperationTable ::= { dot11mac 1 }
-- dot11CountersTable ::= { dot11mac 2 }
-- dot11GroupAddressesTable ::= { dot11mac 3 }
-- dot11EDCATable ::= { dot11mac 4 }
-- dot11QAPEDCATable ::= { dot11mac 5 }
-- dot11QosCountersTable ::= { dot11mac 6 }
-- dot11ResourceInfoTable ::= { dot11mac 7 }
-- Resource Type ID
dot11res OBJECT IDENTIFIER ::= { ieee802dot11 3 }
dot11resAttribute OBJECT IDENTIFIER ::= { dot11res 1 }
-- PHY Attributes
-- DEFINED AS "The PHY object class provides the necessary support
-- for required PHY operational information that may vary from PHY
-- to PHY and from STA to STA to be communicated to upper layers."
dot11phy OBJECT IDENTIFIER ::= { ieee802dot11 4 }
-- PHY GROUPS
-- dot11PhyOperationTable ::= { dot11phy 1 }
-- dot11PhyAntennaTable ::= { dot11phy 2 }
-- dot11PhyTxPowerTable ::= { dot11phy 3 }
-- dot11PhyFHSSTable ::= { dot11phy 4 }
-- dot11PhyDSSSTable ::= { dot11phy 5 }
-- dot11PhyIRTable ::= { dot11phy 6 }
-- dot11RegDomainsSupportedTable ::= { dot11phy 7 }
-- dot11AntennasListTable ::= { dot11phy 8 }
-- dot11SupportedDataRatesTxTable ::= { dot11phy 9 }
-- dot11SupportedDataRatesRxTable ::= { dot11phy 10 }
-- dot11PhyOFDMTable ::= { dot11phy 11 }
-- dot11PhyHRDSSSTable ::= { dot11phy 12 }
-- dot11HoppingPatternTable ::= { dot11phy 13 }
-- dot11PhyERPTable ::= { dot11phy 14 }
-- dot11PhyHTTable ::= { dot11phy 15 }
-- dot11SupportedMCSTxTable ::= { dot11phy 16 }
-- dot11SupportedMCSRxTable ::= { dot11phy 17 }
-- dot11TransmitBeamformingConfigTable ::= { dot11phy 18 }
-- **********************************************************************
-- * Textual conventions for 802 definitions
-- **********************************************************************
WEPKeytype ::= TEXTUAL-CONVENTION
STATUS current
DESCRIPTION "Represents the type of WEP key."
SYNTAX OCTET STRING (SIZE (5))
TSFType ::= TEXTUAL-CONVENTION
STATUS current
DESCRIPTION "Represents the type of TSF."
SYNTAX OCTET STRING (SIZE (8))
-- **********************************************************************
-- * MIB attribute OBJECT-TYPE definitions follow
-- **********************************************************************
-- **********************************************************************
-- * dot11StationConfig TABLE
-- **********************************************************************
dot11StationConfigTable OBJECT-TYPE
SYNTAX SEQUENCE OF Dot11StationConfigEntry
MAX-ACCESS not-accessible
STATUS current
DESCRIPTION
"Station Configuration attributes. In tabular form to allow for multiple
instances on an agent."
::= { dot11smt 1 }
dot11StationConfigEntry OBJECT-TYPE
SYNTAX Dot11StationConfigEntry
MAX-ACCESS not-accessible
STATUS current
DESCRIPTION
"An entry in the dot11StationConfigTable. It is possible for there to be
multiple IEEE 802.11 interfaces on one agent, each with its unique MAC
address. The relationship between an IEEE 802.11 interface and an interface
in the context of the Internet-standard MIB is one-to-one. As such,
the value of an ifIndex object instance can be directly used to identify
corresponding instances of the objects defined herein.
ifIndex - Each IEEE 802.11 interface is represented by an ifEntry. Interface
tables in this MIB module are indexed by ifIndex."
INDEX { ifIndex }
::= { dot11StationConfigTable 1 }
Dot11StationConfigEntry ::= SEQUENCE
{
dot11StationID MacAddress,
dot11MediumOccupancyLimit Unsigned32,
dot11CFPollable TruthValue,
dot11CFPPeriod Unsigned32,
dot11CFPMaxDuration Unsigned32,
dot11AuthenticationResponseTimeOut Unsigned32,
dot11PrivacyOptionImplemented TruthValue,
dot11PowerManagementMode INTEGER,
dot11DesiredSSID OCTET STRING,
dot11DesiredBSSType INTEGER,
dot11OperationalRateSet OCTET STRING,
dot11BeaconPeriod Unsigned32,
dot11DTIMPeriod Unsigned32,
dot11AssociationResponseTimeOut Unsigned32,
dot11DisassociateReason Unsigned32,
dot11DisassociateStation MacAddress,
dot11DeauthenticateReason Unsigned32,
dot11DeauthenticateStation MacAddress,
dot11AuthenticateFailStatus Unsigned32,
dot11AuthenticateFailStation MacAddress,
dot11MultiDomainCapabilityImplemented TruthValue,
dot11MultiDomainCapabilityActivated TruthValue,
dot11CountryString OCTET STRING,
dot11SpectrumManagementImplemented TruthValue,
dot11SpectrumManagementRequired TruthValue,
dot11RSNAOptionImplemented TruthValue,
dot11RSNAPreauthenticationImplemented TruthValue,
dot11OperatingClassesImplemented TruthValue,
dot11OperatingClassesRequired TruthValue,
dot11QosOptionImplemented TruthValue,
dot11ImmediateBlockAckOptionImplemented TruthValue,
dot11DelayedBlockAckOptionImplemented TruthValue,
dot11DirectOptionImplemented TruthValue,
dot11APSDOptionImplemented TruthValue,
dot11QAckOptionImplemented TruthValue,
dot11QBSSLoadImplemented TruthValue,
dot11QueueRequestOptionImplemented TruthValue,
dot11TXOPRequestOptionImplemented TruthValue,
dot11MoreDataAckOptionImplemented TruthValue,
dot11AssociateInNQBSS TruthValue,
dot11DLSAllowedInQBSS TruthValue,
dot11DLSAllowed TruthValue,
dot11AssociateStation MacAddress,
dot11AssociateID Unsigned32,
dot11AssociateFailStation MacAddress,
dot11AssociateFailStatus Unsigned32,
dot11ReassociateStation MacAddress,
dot11ReassociateID Unsigned32,
dot11ReassociateFailStation MacAddress,
dot11ReassociateFailStatus Unsigned32,
dot11RadioMeasurementImplemented TruthValue,
dot11RadioMeasurementActivated TruthValue,
dot11RMMeasurementProbeDelay Unsigned32,
dot11RMMeasurementPilotPeriod Unsigned32,
dot11RMLinkMeasurementActivated TruthValue,
dot11RMNeighborReportActivated TruthValue,
dot11RMParallelMeasurementsActivated TruthValue,
dot11RMRepeatedMeasurementsActivated TruthValue,
dot11RMBeaconPassiveMeasurementActivated TruthValue,
dot11RMBeaconActiveMeasurementActivated TruthValue,
dot11RMBeaconTableMeasurementActivated TruthValue,
dot11RMBeaconMeasurementReportingConditionsActivated TruthValue,
dot11RMFrameMeasurementActivated TruthValue,
dot11RMChannelLoadMeasurementActivated TruthValue,
dot11RMNoiseHistogramMeasurementActivated TruthValue,
dot11RMStatisticsMeasurementActivated TruthValue,
dot11RMLCIMeasurementActivated TruthValue,
dot11RMLCIAzimuthActivated TruthValue,
dot11RMTransmitStreamCategoryMeasurementActivated TruthValue,
dot11RMTriggeredTransmitStreamCategoryMeasurementActivated
TruthValue,
dot11RMAPChannelReportActivated TruthValue,
dot11RMMIBActivated TruthValue,
dot11RMMaxMeasurementDuration Unsigned32,
dot11RMNonOperatingChannelMaxMeasurementDuration Unsigned32,
dot11RMMeasurementPilotTransmissionInformationActivated
TruthValue,
dot11RMMeasurementPilotActivated Unsigned32,
dot11RMNeighborReportTSFOffsetActivated TruthValue,
dot11RMRCPIMeasurementActivated TruthValue,
dot11RMRSNIMeasurementActivated TruthValue,
dot11RMBSSAverageAccessDelayActivated TruthValue,
dot11RMBSSAvailableAdmissionCapacityActivated TruthValue,
dot11RMAntennaInformationActivated TruthValue,
dot11FastBSSTransitionImplemented TruthValue,
dot11LCIDSEImplemented TruthValue,
dot11LCIDSERequired TruthValue,
dot11DSERequired TruthValue,
dot11ExtendedChannelSwitchActivated TruthValue,
dot11RSNAProtectedManagementFramesActivated
TruthValue,
dot11RSNAUnprotectedManagementFramesAllowed TruthValue,
dot11AssociationSAQueryMaximumTimeout Unsigned32,
dot11AssociationSAQueryRetryTimeout Unsigned32,
dot11HighThroughputOptionImplemented TruthValue,
dot11RSNAPBACRequired TruthValue,
dot11PSMPOptionImplemented TruthValue,
dot11TunneledDirectLinkSetupImplemented TruthValue,
dot11TDLSPeerUAPSDBufferSTAActivated TruthValue,
dot11TDLSPeerPSMActivated TruthValue,
dot11TDLSPeerUAPSDIndicationWindow Unsigned32,
dot11TDLSChannelSwitchingActivated TruthValue,
dot11TDLSPeerSTAMissingAckRetryLimit Unsigned32,
dot11TDLSResponseTimeout Unsigned32,
dot11OCBActivated TruthValue,
dot11TDLSProbeDelay Unsigned32,
dot11TDLSDiscoveryRequestWindow Unsigned32,
dot11TDLSACDeterminationInterval Unsigned32,
dot11WirelessManagementImplemented TruthValue,
dot11BssMaxIdlePeriod Unsigned32,
dot11BssMaxIdlePeriodOptions OCTET STRING,
dot11TIMBroadcastInterval Unsigned32,
dot11TIMBroadcastOffset Integer32,
dot11TIMBroadcastHighRateTIMRate Unsigned32,
dot11TIMBroadcastLowRateTIMRate Unsigned32,
dot11StatsMinTriggerTimeout Unsigned32,
dot11RMCivicMeasurementActivated TruthValue,
dot11RMIdentifierMeasurementActivated TruthValue,
dot11TimeAdvertisementDTIMInterval Unsigned32,
dot11TimeAdvertisementTimeError OCTET STRING,
dot11TimeAdvertisementTimeValue OCTET STRING,
dot11RM3rdPartyMeasurementActivated TruthValue,
dot11InterworkingServiceImplemented TruthValue,
dot11InterworkingServiceActivated TruthValue,
dot11QosMapImplemented TruthValue,
dot11QosMapActivated TruthValue,
dot11EBRImplemented TruthValue,
dot11EBRActivated TruthValue,
dot11ESNetwork TruthValue,
dot11SSPNInterfaceImplemented TruthValue,
dot11SSPNInterfaceActivated TruthValue,
dot11HESSID MacAddress,
dot11EASImplemented TruthValue,
dot11EASActivated TruthValue,
dot11MSGCFImplemented TruthValue,
dot11MSGCFActivated TruthValue,
dot11MeshActivated TruthValue,
dot11RejectUnadmittedTraffic TruthValue,
dot11BSSBroadcastNullCount Unsigned32
}
dot11StationID OBJECT-TYPE
SYNTAX MacAddress
MAX-ACCESS read-write
STATUS current
DESCRIPTION
"This is a control variable.
It is written by the SME or external management entity.
Changes take effect for the next MLME-START.request primitive.
The purpose of dot11StationID is to allow a manager to identify a station
for its own purposes. This attribute provides for that eventuality while
keeping the true MAC address independent. Its syntax is MAC address, and
the default value is the station's assigned, unique MAC address."
::= { dot11StationConfigEntry 1 }
dot11MediumOccupancyLimit OBJECT-TYPE
SYNTAX Unsigned32 (0..1000)
MAX-ACCESS read-write
STATUS current
DESCRIPTION
"This is a control variable.
It is written by an external management entity.
Changes take effect as soon as practical in the implementation.
This attribute indicates the maximum amount of time, in TU, that a point
coordinator (PC) may control the usage of the wireless medium (WM) without
relinquishing control for long enough to allow at least one instance of
DCF access to the medium. The maximum value of this variable is 1000."
DEFVAL { 100 }
::= { dot11StationConfigEntry 2 }
dot11CFPollable OBJECT-TYPE
SYNTAX TruthValue
MAX-ACCESS read-only
STATUS current
DESCRIPTION
"This is a capability variable.
Its value is determined by device capabilities.
When this attribute is true, it indicates that the STA is able to respond
to a CF-Poll with a data frame within a SIFS time. This attribute is false
if the STA is not able to respond to a CF-Poll with a data frame within a
SIFS time."
::= { dot11StationConfigEntry 3 }
dot11CFPPeriod OBJECT-TYPE
SYNTAX Unsigned32 (0..255)
MAX-ACCESS read-only
STATUS current
DESCRIPTION
"This is a status variable.
In an AP, it is written by the MAC when it receives an MLME-START.request
primitive.
In a non-AP STA, it is written by the MAC when it receives an updated CF
Parameter Set in a Beacon frame.
The attribute describes the number of DTIM intervals between the start of
CFPs. It is modified by MLME-START.request primitive."
::= { dot11StationConfigEntry 4 }
dot11CFPMaxDuration OBJECT-TYPE
SYNTAX Unsigned32 (0..65535)
MAX-ACCESS read-only
STATUS current
DESCRIPTION
"This is a status variable.
In an AP, it is written by the MAC when it receives an MLME-START.request
primitive.
In a non-AP STA, it is written by the MAC when it receives an updated CF
Parameter Set in a Beacon frame.
The attribute describes the maximum duration of the CFP in TU that may be
generated by the PCF. It is modified by MLME-START.request primitive."
::= { dot11StationConfigEntry 5 }
dot11AuthenticationResponseTimeOut OBJECT-TYPE
SYNTAX Unsigned32 (1..4294967295)
MAX-ACCESS read-write
STATUS current
DESCRIPTION
"This is a control variable.
It is written by an external management entity.
Changes take effect for the next Authentication frame.
This attribute specifies the number of time units (TUs) that a responding
STA should wait for the next frame in the authentication sequence."
::= { dot11StationConfigEntry 6 }
dot11PrivacyOptionImplemented OBJECT-TYPE
SYNTAX TruthValue
MAX-ACCESS read-only
STATUS current
DESCRIPTION
"This is a capability variable.
Its value is determined by device capabilities.
This attribute, when true, indicates that the IEEE 802.11 WEP
option is implemented."
DEFVAL { false }
::= { dot11StationConfigEntry 7 }
dot11PowerManagementMode OBJECT-TYPE
SYNTAX INTEGER { active(1), powersave(2) }
MAX-ACCESS read-only
STATUS current
DESCRIPTION
"This is a status variable.
It is written by the MAC when an MLME-POWERMGT.request primitive is
received.
This attribute specifies the power management mode of the STA. When equal
to active, it indicates that the station is not in power save (PS) mode.
When equal to powersave, it indicates that the station is in power save
mode. The power management mode is transmitted in all frames according to
the rules in 8.2.4.1.8."
::= { dot11StationConfigEntry 8 }
dot11DesiredSSID OBJECT-TYPE
SYNTAX OCTET STRING (SIZE(0..32))
MAX-ACCESS read-write
STATUS current
DESCRIPTION
"This is a control variable.
It is written by an external management entity.
Changes take effect for the next MLME-SCAN.request primitive.
This attribute reflects the Service Set ID (SSID) used in the SSID parameter
of the most recent MLME-SCAN.request primitive. This value may be
modified by an external management entity and used by the local SME to
make decisions about the Scanning process."
::= { dot11StationConfigEntry 9 }
dot11DesiredBSSType OBJECT-TYPE
SYNTAX INTEGER { infrastructure(1), independent(2), any(3) }
MAX-ACCESS read-write
STATUS current
DESCRIPTION
"This is a control variable.
It is written by an external management entity.
Changes take effect for the next MLME-SCAN.request primitive.
This attribute specifies the type of BSS the station uses when scanning
for a BSS with which to synchronize. This value is used to filter Probe
Response frames and Beacon frames. When equal to infrastructure, the station
synchronizes only with a BSS in which the Capability Information
field has the ESS subfield equal to 1. When equal to independent, the station
synchronizes only with a BSS whose Capability Information field has
the IBSS subfield equal to 1. When equal to any, the station may synchronize
to either type of BSS."
::= { dot11StationConfigEntry 10 }
dot11OperationalRateSet OBJECT-TYPE
SYNTAX OCTET STRING (SIZE(1..126))
MAX-ACCESS read-only
STATUS current
DESCRIPTION
"This is a status variable.
It is written by the SME when joining or establishing a BSS.
This attribute specifies the set of non-HT data rates at which the station
may transmit data. The attribute that specifies the set of HT data rates
is dot11HTOperationalMCSSet. Each octet contains a value representing a
rate. Each rate is within the range from 2 to 127, corresponding to data
rates in increments of 500 kbit/s from 1 Mb/s to 63.5 Mb/s, and is supported
(as indicated in the supported rates table) for receiving data.
This value is reported in transmitted Beacon, Probe Request, Probe
Response, Association Request, Association Response, Reassociation
Request, and Reassociation Response frames, and is used to determine
whether a BSS with which the station desires to synchronize is suitable.
It is also used when starting a BSS, as specified in 6.3.4."
::= { dot11StationConfigEntry 11 }
dot11BeaconPeriod OBJECT-TYPE
SYNTAX Unsigned32 (1..65535)
MAX-ACCESS read-write
STATUS current
DESCRIPTION
"This is a control variable.
It is written by an external management entity.
Changes take effect for the next MLME-START.request primitive.
This attribute specifies the number of TUs that a station uses for scheduling
Beacon transmissions. This value is transmitted in Beacon and Probe
Response frames."
::= { dot11StationConfigEntry 12 }
dot11DTIMPeriod OBJECT-TYPE
SYNTAX Unsigned32(1..255)
MAX-ACCESS read-write
STATUS current
DESCRIPTION
"This is a control variable.
It is written by an external management entity.
Changes take effect for the next MLME-START.request primitive.
This attribute specifies the number of beacon intervals that elapse
between transmission of Beacon frames containing a TIM element whose DTIM
Count field is 0. This value is transmitted in the DTIM Period field of
Beacon frames."
::= { dot11StationConfigEntry 13 }
dot11AssociationResponseTimeOut OBJECT-TYPE
SYNTAX Unsigned32 (1..4294967295)
MAX-ACCESS read-write
STATUS current
DESCRIPTION
"This is a control variable.
It is written by an external management entity.
Changes take effect as soon as practical in the implementation.
This attribute specifies the number of TU that a requesting STA should
wait for a response to a transmitted association-request MMPDU."
::= { dot11StationConfigEntry 14 }
dot11DisassociateReason OBJECT-TYPE
SYNTAX Unsigned32(0..65535)
MAX-ACCESS read-only
STATUS current
DESCRIPTION
"This is a status variable.
It is written by the MAC when a STA disassociates.
This attribute holds the most recently transmitted Reason Code in a Disassociation
frame. If no Disassociation frame has been transmitted, the
value of this attribute is 0."
REFERENCE "IEEE Std 802.11-2012, 8.4.1.7"
::= { dot11StationConfigEntry 15 }
dot11DisassociateStation OBJECT-TYPE
SYNTAX MacAddress
MAX-ACCESS read-only
STATUS current
DESCRIPTION
"This is a status variable.
It is written by the MAC when a STA disassociates.
This attribute holds the MAC address from the Address 1 field of the most
recently transmitted Disassociation frame. If no Disassociation frame has
been transmitted, the value of this attribute is 0."
::= { dot11StationConfigEntry 16 }
dot11DeauthenticateReason OBJECT-TYPE
SYNTAX Unsigned32(0..65535)
MAX-ACCESS read-only
STATUS current
DESCRIPTION
"This is a status variable.
It is written by the MAC when a STA deauthenticates.
This attribute holds the most recently transmitted Reason Code in a Deauthentication
frame. If no Deauthentication frame has been transmitted, the
value of this attribute is 0."
REFERENCE "IEEE Std 802.11-2012, 8.4.1.7"
::= { dot11StationConfigEntry 17 }
dot11DeauthenticateStation OBJECT-TYPE
SYNTAX MacAddress
MAX-ACCESS read-only
STATUS current
DESCRIPTION
"This is a status variable.
It is written by the MAC when a STA deauthenticates.
This attribute holds the MAC address from the Address 1 field of the most
recently transmitted Deauthentication frame. If no Deauthentication frame
has been transmitted, the value of this attribute is 0."
::= { dot11StationConfigEntry 18 }
dot11AuthenticateFailStatus OBJECT-TYPE
SYNTAX Unsigned32(0..65535)
MAX-ACCESS read-only
STATUS current
DESCRIPTION
"This is a status variable.
It is written by the MAC when a STA fails to authenticate.
This attribute holds the most recently transmitted Status Code in a failed
Authentication frame. If no failed Authentication frame has been transmitted,
the value of this attribute is 0."
REFERENCE "IEEE Std 802.11-2012, 8.4.1.9"
::= { dot11StationConfigEntry 19 }
dot11AuthenticateFailStation OBJECT-TYPE
SYNTAX MacAddress
MAX-ACCESS read-only
STATUS current
DESCRIPTION
"This is a status variable.
It is written by the MAC when a STA fails to authenticate.
This attribute holds the MAC address from the Address 1 field of the most
recently transmitted failed Authentication frame. If no failed Authentication
frame has been transmitted, the value of this attribute is 0."
::= { dot11StationConfigEntry 20 }
dot11MultiDomainCapabilityImplemented OBJECT-TYPE
SYNTAX TruthValue
MAX-ACCESS read-only
STATUS current
DESCRIPTION
"This is a capability variable.
Its value is determined by device capabilities.
This attribute, when true, indicates that the station implementation is
capable of supporting multiple regulatory domains. The capability is disabled,
otherwise."
DEFVAL { false }
::= { dot11StationConfigEntry 21 }
dot11MultiDomainCapabilityActivated OBJECT-TYPE
SYNTAX TruthValue
MAX-ACCESS read-write
STATUS current
DESCRIPTION
"This is a control variable.
It is written by the SME or external management entity.
Changes take effect for the next MLME-START.request primitive.
This attribute, when true, indicates that the capability of the station to
operate in multiple regulatory domains is enabled."
DEFVAL { false }
::= { dot11StationConfigEntry 22 }
dot11CountryString OBJECT-TYPE
SYNTAX OCTET STRING (SIZE(3))
MAX-ACCESS read-only
STATUS current
DESCRIPTION
"This is a control variable.
It is written by the SME.
Changes take effect for the next MLME-START.request primitive.
This attribute identifies the country or noncountry entity in which the
station is operating. If it is a country, the first two octets of this
string is the two character country code as described in document ISO/IEC
3166-1. The third octet is one of the following:
1. an ASCII space character, if the regulations under which the station is
operating encompass all environments for the current frequency band in the
country,
2. an ASCII 'O' character, if the regulations under which the station is
operating are for an Outdoor environment only, or
3. an ASCII 'I' character, if the regulations under which the station is
operating are for an Indoor environment only.
4. an ASCII 'X' character, if the station is operating under a noncountry
entity. The first two octets of the noncountry entity is two ASCII 'XX'
characters.
5. the binary representation of the Operating Class table number currently
in use, from the set of tables defined in Annex E, e.g. Table E-1 is represented
as x'01'."
::= { dot11StationConfigEntry 23 }
dot11SpectrumManagementImplemented OBJECT-TYPE
SYNTAX TruthValue
MAX-ACCESS read-only
STATUS current
DESCRIPTION
"This is a capability variable.
Its value is determined by device capabilities.
This attribute, when true, indicates that the station implementation is
capable of supporting spectrum management. The capability is disabled otherwise."
DEFVAL { false }
::= { dot11StationConfigEntry 24 }
dot11SpectrumManagementRequired OBJECT-TYPE
SYNTAX TruthValue
MAX-ACCESS read-write
STATUS current
DESCRIPTION
"This is a control variable.
It is written by the SME or external management entity.
Changes take effect for the next MLME-START.request primitive.
A STA uses the defined TPC and DFS procedures if this attribute is true;
otherwise it does not use the defined TPC and DFS procedures."
DEFVAL { false }
::= { dot11StationConfigEntry 25 }
dot11RSNAOptionImplemented OBJECT-TYPE
SYNTAX TruthValue
MAX-ACCESS read-only
STATUS current
DESCRIPTION
"This is a capability variable.
Its value is determined by device capabilities.
This variable indicates whether the entity is RSNA-capable."
::= { dot11StationConfigEntry 26 }
dot11RSNAPreauthenticationImplemented OBJECT-TYPE
SYNTAX TruthValue
MAX-ACCESS read-only
STATUS current
DESCRIPTION
"This is a capability variable.
Its value is determined by device capabilities.
This variable indicates whether the entity supports RSNA preauthentication.
This cannot be true unless dot11RSNAOptionImplemented is true."
::= { dot11StationConfigEntry 27 }
dot11OperatingClassesImplemented OBJECT-TYPE
SYNTAX TruthValue
MAX-ACCESS read-only
STATUS current
DESCRIPTION
"This is a capability variable.
Its value is determined by device capabilities.
This attribute, when true, indicates that the station implementation is
capable of supporting operating classes. The capability is disabled otherwise."
DEFVAL { false }
::= { dot11StationConfigEntry 28 }
dot11OperatingClassesRequired OBJECT-TYPE
SYNTAX TruthValue
MAX-ACCESS read-write
STATUS current
DESCRIPTION
"This is a control variable.
It is written by the SME or external management entity.
Changes take effect for the next MLME-START.request primitive.
A STA uses the defined operating classes procedures if this attribute is
true."
DEFVAL { false }
::= { dot11StationConfigEntry 29 }
dot11QosOptionImplemented OBJECT-TYPE
SYNTAX TruthValue
MAX-ACCESS read-only
STATUS current
DESCRIPTION
"This is a capability variable.
Its value is determined by device capabilities.
This attribute, when true, indicates that the station implementation is
capable of supporting QoS. The capability is disabled, otherwise."
DEFVAL { false }
::= { dot11StationConfigEntry 30}
dot11ImmediateBlockAckOptionImplemented OBJECT-TYPE
SYNTAX TruthValue
MAX-ACCESS read-only
STATUS current
DESCRIPTION
"This is a capability variable.
Its value is determined by device capabilities.
This attribute, when true, indicates that the station implementation is
capable of supporting Immediate Block Ack. The capability is disabled,
otherwise."
DEFVAL { false }
::= { dot11StationConfigEntry 31}
dot11DelayedBlockAckOptionImplemented OBJECT-TYPE
SYNTAX TruthValue
MAX-ACCESS read-only
STATUS current
DESCRIPTION
"This is a capability variable.
Its value is determined by device capabilities.
This attribute, when true, indicates that the station implementation is
capable of supporting Delayed Block Ack. The capability is disabled, otherwise."
DEFVAL { false }
::= { dot11StationConfigEntry 32 }
dot11DirectOptionImplemented OBJECT-TYPE
SYNTAX TruthValue
MAX-ACCESS read-only
STATUS current
DESCRIPTION
"This is a capability variable.
Its value is determined by device capabilities.
This attribute, when true, indicates that the station implementation is
capable of sending and receiving frames from a non-AP STA in the BSS. The
capability is disabled, otherwise."
DEFVAL { false }
::= { dot11StationConfigEntry 33 }
dot11APSDOptionImplemented OBJECT-TYPE
SYNTAX TruthValue
MAX-ACCESS read-only
STATUS current
DESCRIPTION
"This is a capability variable.
Its value is determined by device capabilities.
This attribute is available only at an AP. When true, this attribute indicates
that the AP implementation is capable of delivering data and polls
to stations using APSD."
::= { dot11StationConfigEntry 34 }
dot11QAckOptionImplemented OBJECT-TYPE
SYNTAX TruthValue
MAX-ACCESS read-only
STATUS current
DESCRIPTION
"This is a capability variable.
Its value is determined by device capabilities.
This attribute, when true, indicates that the station implementation is
capable of interpreting the CF-Ack bit in a received frame of type data
even if the frame is not directed to the QoS station. The capability is
disabled, otherwise. A STA is capable of interpreting the CF-Ack bit in a
received data frame if that station is the recipient of the data frame,
regardless of the value of this MIB variable."
DEFVAL { false }
::= { dot11StationConfigEntry 35 }
dot11QBSSLoadImplemented OBJECT-TYPE
SYNTAX TruthValue
MAX-ACCESS read-only
STATUS current
DESCRIPTION
"This is a capability variable.
Its value is determined by device capabilities.
This attribute is available only at an AP. This attribute, when true,
indicates that the AP implementation is capable of generating and transmitting
the BSS load element in the Beacon and Probe Response frames. The
capability is disabled, otherwise."
DEFVAL { false }
::= { dot11StationConfigEntry 36 }
dot11QueueRequestOptionImplemented OBJECT-TYPE
SYNTAX TruthValue
MAX-ACCESS read-only
STATUS current
DESCRIPTION
"This is a capability variable.
Its value is determined by device capabilities.
This attribute is available only at an AP. This attribute, when true,
indicates that the AP is capable of processing the Queue Size field in QoS
Control field of QoS Data type frames. The capability is disabled, otherwise."
DEFVAL { false }
::= { dot11StationConfigEntry 37 }
dot11TXOPRequestOptionImplemented OBJECT-TYPE
SYNTAX TruthValue
MAX-ACCESS read-only
STATUS current
DESCRIPTION
"This is a capability variable.
Its value is determined by device capabilities.
This attribute is available only at an AP. This attribute, when true,
indicates that the AP is capable of processing the TXOP Duration requested
field in QoS Control field of QoS Data type frames. The capability is disabled,
otherwise."
DEFVAL { false }
::= { dot11StationConfigEntry 38 }
dot11MoreDataAckOptionImplemented OBJECT-TYPE
SYNTAX TruthValue
MAX-ACCESS read-only
STATUS current
DESCRIPTION
"This is a capability variable.
Its value is determined by device capabilities.
This attribute, when true, indicates that the station implementation is
capable of interpreting the More Data bit in the ACK frames. The capability
is disabled, otherwise."
DEFVAL { false }
::= { dot11StationConfigEntry 39 }
dot11AssociateInNQBSS OBJECT-TYPE
SYNTAX TruthValue
MAX-ACCESS read-write
STATUS current
DESCRIPTION
"This is a control variable.
It is written by an external management entity.
Changes take effect as soon as practical in the implementation.
This attribute, when true, indicates that the station may associate in a
non-QoS BSS. When false, this attribute indicates that the station does
not associate in a non-QoS BSS."
DEFVAL { true }
::= { dot11StationConfigEntry 40 }
dot11DLSAllowedInQBSS OBJECT-TYPE
SYNTAX TruthValue
MAX-ACCESS read-write
STATUS current
DESCRIPTION
"This is a control variable.
It is written by an external management entity.
Changes take effect as soon as practical in the implementation.
This attribute available at the AP, when true, indicates that STAs may set
up DLS and communicate using DLS with other STAs in the BSS. When false,
this attribute indicates that the stations do not set up DLS nor communicate
with other STAs using DLS in the BSS."
DEFVAL { true }
::= { dot11StationConfigEntry 41 }
dot11DLSAllowed OBJECT-TYPE
SYNTAX TruthValue
MAX-ACCESS read-write
STATUS current
DESCRIPTION
"This is a control variable.
It is written by an external management entity.
Changes take effect as soon as practical in the implementation.
This attribute available at non-AP STAs, when true, indicates that the STA
may set up DLS or accept DLS Requests, and communicate with other STAs in
the BSS using DLS. When false, this attribute indicates that the STA does
not set up DLS nor accept DLS, nor communicate with other STAs in the BSS
using DLS."
DEFVAL { true }
::= { dot11StationConfigEntry 42}
dot11AssociateStation OBJECT-TYPE
SYNTAX MacAddress
MAX-ACCESS read-only
STATUS current
DESCRIPTION
"This is a status variable.
It is written by the MAC when a STA associates.
This attribute indicates the MAC address from the Address 1 field of the
most recently transmitted association response frame. If no association
response frame has been transmitted, the value of this attribute is 0."
::= { dot11StationConfigEntry 43 }
dot11AssociateID OBJECT-TYPE
SYNTAX Unsigned32(0..2007)
MAX-ACCESS read-only
STATUS current
DESCRIPTION
"This is a status variable.
It is written by the MAC when a STA associates.
This attribute indicates the Association ID from the most recently transmitted
association response frame. If no association response frame has
been transmitted, the value of this attribute is 0."
::= { dot11StationConfigEntry 44 }
dot11AssociateFailStation OBJECT-TYPE
SYNTAX MacAddress
MAX-ACCESS read-only
STATUS current
DESCRIPTION
"This is a status variable.
It is written by the MAC when a STA fails to associate.
This attribute indicates the MAC address from the Address 1 field of the
most recently transmitted failed association response frame. If no failed
association response frame has been transmitted, the value of this attribute
is 0."
::= { dot11StationConfigEntry 45 }
dot11AssociateFailStatus OBJECT-TYPE
SYNTAX Unsigned32(0..65535)
MAX-ACCESS read-only
STATUS current
DESCRIPTION
"This is a status variable.
It is written by the MAC when a STA fails to associate.
This attribute indicates the most recently transmitted Status Code in a
failed association response frame. If no failed association response frame
has been transmitted, the value of this attribute is 0."
::= { dot11StationConfigEntry 46 }
dot11ReassociateStation OBJECT-TYPE
SYNTAX MacAddress
MAX-ACCESS read-only
STATUS current
DESCRIPTION
"This is a status variable.
It is written by the MAC when a STA reassociates.
This attribute indicates the MAC address from the Address 1 field of the
most recently transmitted reassociation response frame. If no reassociation
response frame has been transmitted, the value of this attribute is
0."
::= { dot11StationConfigEntry 47 }
dot11ReassociateID OBJECT-TYPE
SYNTAX Unsigned32(0..2007)
MAX-ACCESS read-only
STATUS current
DESCRIPTION
"This is a status variable.
It is written by the MAC when a STA reassociates.
This attribute indicates the Association ID from the most recently transmitted
reassociation response frame. If no reassociation response frame
has been transmitted, the value of this attribute is 0."
::= { dot11StationConfigEntry 48 }
dot11ReassociateFailStation OBJECT-TYPE
SYNTAX MacAddress
MAX-ACCESS read-only
STATUS current
DESCRIPTION
"This is a status variable.
It is written by the MAC when a STA fails to reassociate.
This attribute indicates the MAC address from the Address 1 field of the
most recently transmitted failed reassociation response frame. If no
failed reassociation response frame has been transmitted, the value of
this attribute is 0."
::= { dot11StationConfigEntry 49 }
dot11ReassociateFailStatus OBJECT-TYPE
SYNTAX Unsigned32(0..65535)
MAX-ACCESS read-only
STATUS current
DESCRIPTION
"This is a status variable.
It is written by the MAC when a STA fails to reassociate.
This attribute indicates the most recently transmitted Status Code in a
failed reassociation response frame. If no failed reassociation response
frame has been transmitted, the value of this attribute is 0."
::= { dot11StationConfigEntry 50 }
dot11RadioMeasurementImplemented OBJECT-TYPE
SYNTAX TruthValue
MAX-ACCESS read-only
STATUS current
DESCRIPTION
"This is a capability variable.
Its value is determined by device capabilities.
This attribute, when true, indicates that the station implementation is
capable of supporting Radio Measurement. Otherwise it is not capable of
performing Radio Measurement."
DEFVAL { false }
::= { dot11StationConfigEntry 51 }
dot11RadioMeasurementActivated OBJECT-TYPE
SYNTAX TruthValue
MAX-ACCESS read-write
STATUS current
DESCRIPTION
"This is a control variable.
It is written by an external management entity when any of the MIB variables
listed in 8.4.2.47 is equal to true.
Changes take effect with the next MLME-START.request primitive or MLMEJOIN.
request primitive.
This attribute, when true, indicates that one or more of the Radio Measurement
Activated Capabilities MIB attributes, listed in 8.4.2.47, are
equal to true. A STA may use the defined Radio Measurement procedures if
this attribute is true."
DEFVAL { false }
::= { dot11StationConfigEntry 52 }
dot11RMMeasurementProbeDelay OBJECT-TYPE
SYNTAX Unsigned32
MAX-ACCESS read-write
STATUS current
DESCRIPTION
"This is a control variable.
It is written by an external management entity.
Changes take effect as soon as practical in the implementation.
The value of ProbeDelay to be used when making a beacon type measurement
with measurement mode active when dot11RMActiveBeaconMeasurementActivated
is true."
::= { dot11StationConfigEntry 53 }
dot11RMMeasurementPilotPeriod OBJECT-TYPE
SYNTAX Unsigned32 (1..255)
MAX-ACCESS read-write
STATUS current
DESCRIPTION
"This is a control variable.
It is written by an external management entity.
Changes take effect as soon as practical in the implementation.
This attribute specifies the number of TUs that a station uses for scheduling
Measurement Pilot transmissions. This value is transmitted in Measurement
Pilot frames. The default period is 25% of dot11BeaconPeriod."
::= { dot11StationConfigEntry 54 }
dot11RMLinkMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Link Measurement is enabled. A
value of false indicates the station has no Link Measurement capability or
that the capability is present but is disabled."
DEFVAL { false }
::= { dot11StationConfigEntry 55 }
dot11RMNeighborReportActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for neighbor report is enabled.
False indicates the station has no neighbor report capability or that the
capability is present but is disabled."
DEFVAL { false }
::= { dot11StationConfigEntry 56 }
dot11RMParallelMeasurementsActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Parallel Measurements is
enabled. False indicates the station has no Parallel Measurements capability
or that the capability is present but is disabled."
DEFVAL { false }
::= { dot11StationConfigEntry 57 }
dot11RMRepeatedMeasurementsActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Repeated Measurements is
enabled. False indicates the station has no Repeated Measurements capability
or that the capability is present but is disabled."
DEFVAL { false }
::= { dot11StationConfigEntry 58 }
dot11RMBeaconPassiveMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Beacon Passive Measurement is
enabled. False indicates the station has no Beacon Passive Measurement
capability or that the capability is present but is disabled."
DEFVAL { false }
::= { dot11StationConfigEntry 59 }
dot11RMBeaconActiveMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Beacon Active Measurement is
enabled. False indicates the station has no Beacon Active Measurement
capability or that the capability is present but is disabled."
DEFVAL { false }
::= { dot11StationConfigEntry 60 }
dot11RMBeaconTableMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Beacon Table Measurement is
enabled. False indicates the station has no Beacon Table Measurement capability
or that the capability is present but is disabled."
DEFVAL { false }
::= { dot11StationConfigEntry 61 }
dot11RMBeaconMeasurementReportingConditionsActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Beacon Measurement Reporting
Conditions is enabled. False indicates the station has no Beacon Measurement
Reporting Conditions capability or that the capability is present but
is disabled."
DEFVAL { false }
::= { dot11StationConfigEntry 62 }
dot11RMFrameMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Frame Measurement is enabled.
False indicates the station has no Frame Measurement capability or that
the capability is present but is disabled."
DEFVAL { false }
::= { dot11StationConfigEntry 63 }
dot11RMChannelLoadMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Channel Load Measurement is
enabled. False indicates the station has no Channel Load Measurement 
capability or that the capability is present but is disabled."
DEFVAL { false }
::= { dot11StationConfigEntry 64 }
dot11RMNoiseHistogramMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Noise Histogram Measurement is
enabled. False indicates the station has no Noise Histogram Measurement
capability or that the capability is present but is disabled."
DEFVAL { false }
::= { dot11StationConfigEntry 65 }
dot11RMStatisticsMeasurementActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for Statistics Measurement is
enabled. False indicates the station has no Statistics Measurement capability
or that the capability is present but is disabled."
DEFVAL { false }
::= { dot11StationConfigEntry 66 }
dot11RMLCIMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for LCI Measurement is enabled.
False indicates the station has no LCI Measurement capability or that the
capability is present but is disabled."
DEFVAL { false }
::= { dot11StationConfigEntry 67 }
dot11RMLCIAzimuthActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for LCI Azimuth Measurement is
enabled. False indicates the station has no LCI Azimuth Measurement capability
or that the capability is present but is disabled."
DEFVAL { false }
::= { dot11StationConfigEntry 68 }
dot11RMTransmitStreamCategoryMeasurementActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for Transmit Stream/Category Measurement
is enabled. False indicates the station has no Transmit Stream/
Category Measurement capability or that the capability is present but is
disabled."
DEFVAL { false }
::= { dot11StationConfigEntry 69 }
dot11RMTriggeredTransmitStreamCategoryMeasurementActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for Triggered Transmit Stream/Category
Measurement is enabled. False indicates the station has no Triggered
Transmit Stream/Category Measurement capability or that the capability is
present but is disabled."
DEFVAL { false }
::= { dot11StationConfigEntry 70 }
dot11RMAPChannelReportActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for AP Channel Report is enabled.
False indicates the station has no AP Channel Report capability or that
the capability is present but is disabled."
DEFVAL { false }
::= { dot11StationConfigEntry 71 }
dot11RMMIBActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for RM MIB is enabled. False indicates
the station has no RM MIB capability or that the capability is present
but is disabled. See RM MIB details."
DEFVAL { false }
::= { dot11StationConfigEntry 72 }
dot11RMMaxMeasurementDuration OBJECT-TYPE
SYNTAX Unsigned32(0 .. 7)
MAX-ACCESS read-write
STATUS current
DESCRIPTION
"This is a control variable.
It is written by an external management entity.
Changes take effect as soon as practical in the implementation.
This attribute indicates the maximum measurement duration for operating
channel measurements, where
Max Measurement Duration in TUs =
(2 ** (dot11RMMaxMeasurementDuration - 4)) * BeaconInterval
Further details are provided in 10.11.4"
::= { dot11StationConfigEntry 73 }
dot11RMNonOperatingChannelMaxMeasurementDuration OBJECT-TYPE
SYNTAX Unsigned32(0 .. 7)
MAX-ACCESS read-write
STATUS current
DESCRIPTION
"This is a control variable.
It is written by an external management entity.
Changes take effect for the next MLME-START.request primitive or MLMEJOIN.
request primitive.
This attribute indicates the maximum measurement duration for nonoperating
channel measurements, where
Non-OpMax Measurement Duration in TUs =
(2 ** (dot11RMNonOperatingChannelMaxMeasurementDuration - 4))
* BeaconInterval
Further details are provided in 10.11.4"
::= { dot11StationConfigEntry 74 }
dot11RMMeasurementPilotTransmissionInformationActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for Measurement Pilot Transmission
information is enabled. False indicates the station has no Measurement
Pilot Transmission information capability or that the capability is present
but is disabled."
DEFVAL { false }
::= { dot11StationConfigEntry 75 }
dot11RMMeasurementPilotActivated OBJECT-TYPE
SYNTAX Unsigned32(0 .. 7)
MAX-ACCESS read-write
STATUS current
DESCRIPTION
"This is a control variable.
It is written by an external management entity.
Changes take effect as soon as practical in the implementation.
This attribute indicates the station capability for Measurement Pilot. The
value 0 indicates the station has no Measurement Pilot capability or that
the capability is present but is disabled. Activated values 1-7 are
defined in Table 10-7."
DEFVAL { 0 }
::= { dot11StationConfigEntry 76 }
dot11RMNeighborReportTSFOffsetActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for Neighbor Report TSF Offset is
enabled. False indicates the station has no Neighbor Report TSF Offset
capability or that the capability is present but is disabled."
DEFVAL { false }
::= { dot11StationConfigEntry 77 }
dot11RMRCPIMeasurementActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for RCPI Measurement is enabled.
False indicates the station has no RCPI Measurement capability or that the
capability is present but is disabled."
DEFVAL { false }
::= { dot11StationConfigEntry 78 }
dot11RMRSNIMeasurementActivated OBJECT-TYPE
SYNTAX TruthValue
MAX-ACCESS read-write
STATUS current
DESCRIPTION
"This is a control variable.
It is written by an external management entity.
Changes take effect as soon as practical in the implementation.
This attribute, when true, indicates that dot11RadioMeasurementActivated
is true and that the station capability for RSNI Measurement is enabled.
False indicates the station has no RSNI Measurement capability or that the
capability is present but is disabled."
DEFVAL { false }
::= { dot11StationConfigEntry 79 }
dot11RMBSSAverageAccessDelayActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for BSS Average Access Delay is
enabled. False indicates the station has no BSS Average Access Delay capability
or that the capability is present but is disabled."
DEFVAL { false }
::= { dot11StationConfigEntry 80 }
dot11RMBSSAvailableAdmissionCapacityActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for BSS Available Admission Capacity
is enabled. False indicates the station has no BSS Available Admission
Capacity capability or that the capability is present but is disabled."
DEFVAL { false }
::= { dot11StationConfigEntry 81 }
dot11RMAntennaInformationActivated OBJECT-TYPE
SYNTAX TruthValue
MAX-ACCESS read-write
STATUS current
DESCRIPTION
"This is a control variable.
It is written by an external management entity.
Changes take effect for the next MLME-START.request primitive or MLMEJOIN.
request primitive.
This attribute, when true, indicates that dot11RadioMeasurementActivated
is true and that the station capability for Antenna information is
enabled. False indicates the station has no Antenna information capability
or that the capability is present but is disabled."
DEFVAL { false }
::= { dot11StationConfigEntry 82 }
dot11FastBSSTransitionImplemented OBJECT-TYPE
SYNTAX TruthValue
MAX-ACCESS read-only
STATUS current
DESCRIPTION
"This is a capability variable.
Its value is determined by device capabilities.
This object indicates if the entity is fast BSS transition capable."
::= { dot11StationConfigEntry 83 }
dot11LCIDSEImplemented OBJECT-TYPE
SYNTAX TruthValue
MAX-ACCESS read-only
STATUS current
DESCRIPTION
"This is a capability variable.
Its value is determined by device capabilities.
This attribute, when true, indicates that the station implementation is
capable of supporting LCI DSE. The capability is disabled, otherwise."
DEFVAL { false }
::= { dot11StationConfigEntry 84 }
dot11LCIDSERequired OBJECT-TYPE
SYNTAX TruthValue
MAX-ACCESS read-only
STATUS current
DESCRIPTION
"This is a control variable.
It is written by the SME.
A STA uses the Dependent Station Enablement procedures if this attribute
is true."
DEFVAL { false }
::= { dot11StationConfigEntry 85 }
dot11DSERequired OBJECT-TYPE
SYNTAX TruthValue
MAX-ACCESS read-only
STATUS current
DESCRIPTION
"This is a control variable.
It is written by the SME.
This attribute, when true, indicates that the station operation is dependent
on enablement from enabling STAs. This attribute, when false, indicates
that the station operation does not depend on enablement from STAs."
DEFVAL { false }
::= { dot11StationConfigEntry 86 }
dot11ExtendedChannelSwitchActivated OBJECT-TYPE
SYNTAX TruthValue
MAX-ACCESS read-only
STATUS current
DESCRIPTION
"This is a control variable.
It is written by the SME when the device is initialized for operation in a
band defined by an Operating Class.
This attribute, when true, indicates that the station implementation is
capable of supporting Extended Channel Switch Announcement. The capability
is disabled, otherwise."
DEFVAL { false }
::= { dot11StationConfigEntry 87 }
--**********************************************************
--* Management frame protection MIBs
--**********************************************************
dot11RSNAProtectedManagementFramesActivated OBJECT-TYPE
SYNTAX TruthValue
MAX-ACCESS read-write
STATUS current
DESCRIPTION
"This is a control variable.
It is written by an external management entity.
Changes take effect as soon as practical in the implementation.
This variable indicates whether this STA enables management frame protection."
DEFVAL { false }
::= { dot11StationConfigEntry 88}
dot11RSNAUnprotectedManagementFramesAllowed OBJECT-TYPE
SYNTAX TruthValue
MAX-ACCESS read-write
STATUS current
DESCRIPTION
"This is a control variable.
It is written by an external management entity.
Changes take effect as soon as practical in the implementation.
This variable indicates whether this STA supports RSNA STAs which do not
provide robust management frames protection."
DEFVAL { true }
::= { dot11StationConfigEntry 89}
--**********************************************************
--* SA Query Procedure MIBs
--**********************************************************
dot11AssociationSAQueryMaximumTimeout OBJECT-TYPE
SYNTAX Unsigned32 (1..4294967295)
MAX-ACCESS read-write
STATUS current
DESCRIPTION
"This is a control variable.
It is written by an external management entity.
Changes take effect as soon as practical in the implementation.
This attribute specifies the number of time units (TUs) that an AP can
wait, from the scheduling of the first SA Query Request to allow association
process to be started without starting additional SA Query procedure
if a successful SA Query Response is not received."
DEFVAL { 1000 }
::= { dot11StationConfigEntry 90}
dot11AssociationSAQueryRetryTimeout OBJECT-TYPE
SYNTAX Unsigned32 (1..4294967295)
MAX-ACCESS read-write
STATUS current
DESCRIPTION
"This is a control variable.
It is written by an external management entity.
Changes take effect as soon as practical in the implementation.
This attribute specifies the number of time units (TUs) that an AP waits
between issuing two subsequent MLME-SAQuery.request primitive primitives."
DEFVAL { 201 }
::= { dot11StationConfigEntry 91}
dot11HighThroughputOptionImplemented OBJECT-TYPE
SYNTAX TruthValue
MAX-ACCESS read-only
STATUS current
DESCRIPTION
"This is a capability variable.
Its value is determined by device capabilities.
This attribute indicates whether the entity is HT Capable."
::= { dot11StationConfigEntry 92}
dot11RSNAPBACRequired OBJECT-TYPE
SYNTAX TruthValue
MAX-ACCESS read-write
STATUS current
DESCRIPTION
"This is a control variable.
It is written by an external management entity.
Changes take effect as soon as practical in the implementation.
This variable indicates whether this STA requires the Protection of Block
Ack agreements."
DEFVAL { false }
::= { dot11StationConfigEntry 93}
dot11PSMPOptionImplemented OBJECT-TYPE
SYNTAX TruthValue
MAX-ACCESS read-only
STATUS current
DESCRIPTION
"This is a capability variable.
Its value is determined by device capabilities.
This attribute, when true, indicates that the station implementation is
capable of supporting PSMP."
DEFVAL { false }
::= { dot11StationConfigEntry 94 }
dot11TunneledDirectLinkSetupImplemented OBJECT-TYPE
SYNTAX TruthValue
MAX-ACCESS read-only
STATUS current
DESCRIPTION
"This attribute, when true, indicates that the STA implementation is capable
of supporting Tunneled DirectLink Setup."
DEFVAL { false }
::= { dot11StationConfigEntry 95 }
dot11TDLSPeerUAPSDBufferSTAActivated OBJECT-TYPE
SYNTAX TruthValue
MAX-ACCESS read-only
STATUS current
DESCRIPTION
"This attribute, when true, indicates that the STA implementation is capable
of supporting TDLS Peer U-APSD."
DEFVAL { false }
::= { dot11StationConfigEntry 96 }
dot11TDLSPeerPSMActivated OBJECT-TYPE
SYNTAX TruthValue
MAX-ACCESS read-only
STATUS current
DESCRIPTION
"This attribute, when true, indicates that the STA implementation is capable
of supporting TDLS Peer PSM."
DEFVAL { false }
::= { dot11StationConfigEntry 97 }
dot11TDLSPeerUAPSDIndicationWindow OBJECT-TYPE
SYNTAX Unsigned32 (1..256)
MAX-ACCESS read-write
STATUS current
DESCRIPTION
"This attribute indicates the minimum interval in Beacon Intervals between
successive Peer Traffic Indication frames."
DEFVAL { 1 }
::= { dot11StationConfigEntry 98 }
dot11TDLSChannelSwitchingActivated OBJECT-TYPE
SYNTAX TruthValue
MAX-ACCESS read-only
STATUS current
DESCRIPTION
"This attribute, when true, indicates that the STA implementation is capable
of supporting TDLS Channel Switching."
DEFVAL { false }
::= { dot11StationConfigEntry 99 }
dot11TDLSPeerSTAMissingAckRetryLimit OBJECT-TYPE
SYNTAX Unsigned32 (1..100)
MAX-ACCESS read-write
STATUS current
DESCRIPTION
"This attribute indicates the number of times the TDLS STA may retry a
frame for which it does not receive an ACK from TDLS peer STA in power
save mode after the TDLS peer STA does not receive an ACK to an individually
addressed MPDU sent with the EOSP equal to 1 or to an individually
addressed MPDU that initiated a channel switch."
DEFVAL { 3 }
::= { dot11StationConfigEntry 100 }
dot11TDLSResponseTimeout OBJECT-TYPE
SYNTAX Unsigned32 (1..255)
MAX-ACCESS read-write
STATUS current
DESCRIPTION
"This attribute indicates the amount of time in units of seconds the STA
waits before timing out a TDLS setup request."
DEFVAL { 5 }
::= { dot11StationConfigEntry 101 }
dot11OCBActivated OBJECT-TYPE
SYNTAX TruthValue
MAX-ACCESS read-write
STATUS current
DESCRIPTION
"A STA uses the defined outside the context of a BSS procedures if and
only if this attribute is true. The default value of this attribute is
false."
DEFVAL { false }
::= { dot11StationConfigEntry 102 }
dot11TDLSProbeDelay OBJECT-TYPE
SYNTAX Unsigned32 (1..65535)
MAX-ACCESS read-write
STATUS current
DESCRIPTION
"This attribute indicates the amount of time in units of microseconds the
STA waits before transmitting on a new channel, in the absence of traffic
on the channel that causes a CCA state to be created."
DEFVAL { 1000 }
::= { dot11StationConfigEntry 103 }
dot11TDLSDiscoveryRequestWindow OBJECT-TYPE
SYNTAX Unsigned32 (1..255)
MAX-ACCESS read-write
STATUS current
DESCRIPTION
"This attribute indicates the minimum number of DTIM intervals between
successive TDLS Discovery Request frames."
DEFVAL { 2 }
::= { dot11StationConfigEntry 104 }
dot11TDLSACDeterminationInterval OBJECT-TYPE
SYNTAX Unsigned32 (1..255)
MAX-ACCESS read-write
STATUS current
DESCRIPTION
"This attribute indicates the number of seconds during which the lowest AC
of transmitted traffic is determined."
DEFVAL { 1 }
::= { dot11StationConfigEntry 105 }
dot11WirelessManagementImplemented OBJECT-TYPE
SYNTAX TruthValue
MAX-ACCESS read-only
STATUS current
DESCRIPTION
"This is a capability variable.
Its value is determined by device capabilities.
This attribute, when true, indicates that the station implementation is
capable of supporting one or more wireless network management services."
::= { dot11StationConfigEntry 106}
dot11BssMaxIdlePeriod OBJECT-TYPE
SYNTAX Unsigned32 (1..65535)
MAX-ACCESS read-write
STATUS current
DESCRIPTION
"This is a control variable.
It is written by an external management entity or the SME.
Changes take effect as soon as practical in the implementation.
This attribute indicates that the number of 1000 TUs that pass before an
AP disassociates an inactive non-AP STA. This value is transmitted in the
Association Response and Reassociation Response frames."
::= { dot11StationConfigEntry 107}
dot11BssMaxIdlePeriodOptions OBJECT-TYPE
SYNTAX OCTET STRING (SIZE(1))
MAX-ACCESS read-write
STATUS current
DESCRIPTION
"This is a control variable.
It is written by an external management entity or the SME.
Changes take effect as soon as practical in the implementation.
This attribute indicates the options associated with the BSS Max Idle
capability. This value is transmitted in the Association Response and
Reassociation Response frames."
::= { dot11StationConfigEntry 108}
dot11TIMBroadcastInterval OBJECT-TYPE
SYNTAX Unsigned32 (0..255)
MAX-ACCESS read-write
STATUS current
DESCRIPTION
"This is a control variable.
It is written by an external management entity or the SME.
Changes take effect as soon as practical in the implementation.
This attribute indicates the number of beacon periods between TIM frame
transmissions. A value of 0 disables TIM Broadcast for the requesting station."
DEFVAL { 0 }
::= { dot11StationConfigEntry 109}
dot11TIMBroadcastOffset OBJECT-TYPE
SYNTAX Integer32 (-214748364..214748363)
MAX-ACCESS read-write
STATUS current
DESCRIPTION
"This is a control variable.
It is written by an external management entity or the SME.
Changes take effect as soon as practical in the implementation.
This attribute indicates the offset in microseconds with a tolerance of +/
- 4 microseconds relative to the TBTT for which a TIM frame is scheduled
for transmission. The field contains a signed integer."
DEFVAL { 0 }
::= { dot11StationConfigEntry 110}
dot11TIMBroadcastHighRateTIMRate OBJECT-TYPE
SYNTAX Unsigned32 (0..65535)
UNITS "0.5 Mb/s"
MAX-ACCESS read-write
STATUS current
DESCRIPTION
"This is a control variable.
It is written by an external management entity or the SME.
Changes take effect as soon as practical in the implementation.
This attribute indicates the rate used to transmit the high data rate
TIM frame, in units of 0.5 Mb/s. A value of 0 indicates that the high rate
TIM frame is not transmitted."
DEFVAL { 0 }
::= { dot11StationConfigEntry 111}
dot11TIMBroadcastLowRateTIMRate OBJECT-TYPE
SYNTAX Unsigned32 (0..65535)
UNITS "0.5 Mb/s"
MAX-ACCESS read-write
STATUS current
DESCRIPTION
"This is a control variable.
It is written by an external management entity or the SME.
Changes take effect as soon as practical in the implementation.
This attribute indicates the rate used to transmit the low data rate
TIM frame, in units of 0.5 Mb/s. A value of 0 indicates that the low rate
TIM frame is not transmitted."
DEFVAL { 0 }
::= { dot11StationConfigEntry 112}
dot11StatsMinTriggerTimeout OBJECT-TYPE
SYNTAX Unsigned32 (10..7200)
UNITS "seconds"
MAX-ACCESS read-write
STATUS current
DESCRIPTION
"This is a control variable.
It is written by an external management entity or the SME.
Changes take effect as soon as practical in the implementation.
This attribute indicates the minimum allowable value for Triggered Time
out. A Triggered STA Statistics report is generated by the STA after the
timeout if none of the trigger conditions are satisfied."
DEFVAL { 10 }
::= { dot11StationConfigEntry 113 }
dot11RMCivicMeasurementActivated OBJECT-TYPE
SYNTAX TruthValue
MAX-ACCESS read-write
STATUS current
DESCRIPTION
"This is a control variable.
It is written by an external management entity or the SME.
Changes take effect as soon as practical in the implementation.
This attribute, when true, indicates that dot11RadioMeasurementActivated
is true and that the station capability for Location Civic Measurement is
enabled. False indicates the station has no Location Civic Measurement
capability or that the capability is present but is disabled."
DEFVAL { false }
::= { dot11StationConfigEntry 114 }
dot11RMIdentifierMeasurementActivated OBJECT-TYPE
SYNTAX TruthValue
MAX-ACCESS read-write
STATUS current
DESCRIPTION
"This is a control variable.
It is written by an external management entity or the SME.
Changes take effect as soon as practical in the implementation.
This attribute, when true, indicates that dot11RadioMeasurementActivated
is true and that the station capability for Location Identifier Measurement
is enabled. False indicates the station has no Location Identifier
Measurement capability or that the capability is present but is disabled."
DEFVAL { false }
::= { dot11StationConfigEntry 115 }
dot11TimeAdvertisementDTIMInterval OBJECT-TYPE
SYNTAX Unsigned32 (1..255)
UNITS "dtims"
MAX-ACCESS read-write
STATUS current
DESCRIPTION
"This is a control variable.
It is written by an external management entity or the SME.
Changes take effect as soon as practical in the implementation.
This attribute indicates the interval in number of DTIMS when the Time
Advertisement element is included in beacon frames."
DEFVAL { 1 }
::= { dot11StationConfigEntry 116 }
dot11InterworkingServiceImplemented OBJECT-TYPE
SYNTAX TruthValue
MAX-ACCESS read-only
STATUS current
DESCRIPTION
"This is a capability variable.
Its value is determined by device capabilities.
This attribute when true, indicates the STA is capable of interworking
with external networks. A STA setting this to true implements Interworking
Service. When this is false, the STA does not implement Interworking Service."
DEFVAL {false}
::= { dot11StationConfigEntry 117 }
dot11InterworkingServiceActivated OBJECT-TYPE
SYNTAX TruthValue
MAX-ACCESS read-write
STATUS current
DESCRIPTION
"This is a control variable.
It is written by an external management entity or the SME. Changes take
effect as soon as practical in the implementation.
This attribute when true, indicates the capability of the STA to interwork
with external networks is enabled. The capability is disabled otherwise."
DEFVAL {false}
::= { dot11StationConfigEntry 118 }
dot11QosMapImplemented OBJECT-TYPE
SYNTAX TruthValue
MAX-ACCESS read-only
STATUS current
DESCRIPTION
"This is a capability variable.
Its value is determined by device capabilities.
This attribute available at STAs, when true, indicates the STA is capable
of supporting the QoS Map procedures. When this is set to false, the STA
does not implement QoS Map procedures."
DEFVAL {false}
::= { dot11StationConfigEntry 119 }
dot11QosMapActivated OBJECT-TYPE
SYNTAX TruthValue
MAX-ACCESS read-write
STATUS current
DESCRIPTION
"This is a control variable.
It is written by an external management entity or the SME. Changes take
effect as soon as practical in the implementation.
This attribute, when true, indicates the capability of the STA to support
QoS Map procedures is enabled. The capability is disabled otherwise."
DEFVAL {false}
::= { dot11StationConfigEntry 120 }
dot11EBRImplemented OBJECT-TYPE
SYNTAX TruthValue
MAX-ACCESS read-only
STATUS current
DESCRIPTION
"This is a capability variable.
Its value is determined by device capabilities.
This attribute available at STAs, when true, indicates the STA is capable
of supporting Expedited Bandwidth Request procedures. When this is false,
the STA does not implement Expedited Bandwidth Request procedures."
DEFVAL {false}
::= { dot11StationConfigEntry 121 }
dot11EBRActivated OBJECT-TYPE
SYNTAX TruthValue
MAX-ACCESS read-write
STATUS current
DESCRIPTION
"This is a control variable.
It is written by an external management entity or the SME. Changes take
effect as soon as practical in the implementation.
This attribute, when true, indicates the capability of the STA to support
Expedited Bandwidth Request procedures is enabled. The capability is disabled
otherwise."
DEFVAL {false}
::= { dot11StationConfigEntry 122 }
dot11ESNetwork OBJECT-TYPE
SYNTAX TruthValue
MAX-ACCESS read-write
STATUS current
DESCRIPTION
"This is a control variable.
It is written by an external management entity or the SME. Changes take
effect as soon as practical in the implementation.
The emergency services access network type set to true indicates that the
BSS is used exclusively for the purposes of accessing emergency services.
This object is not used by non-AP STAs."
::= { dot11StationConfigEntry 123 }
dot11SSPNInterfaceImplemented OBJECT-TYPE
SYNTAX TruthValue
MAX-ACCESS read-only
STATUS current
DESCRIPTION
"This is a capability variable.
Its value is determined by device capabilities.
This attribute when true, indicates the AP is capable of SSPN Interface
service. When this is false, the STA does not implement SSPN Interface
Service. This object is not used by non-AP STAs. The default value of this
attribute is false."
DEFVAL {false}
::= { dot11StationConfigEntry 124 }
dot11SSPNInterfaceActivated OBJECT-TYPE
SYNTAX TruthValue
MAX-ACCESS read-write
STATUS current
DESCRIPTION
"This is a control variable.
It is written by an external management entity or the SME. Changes take
effect as soon as practical in the implementation.
This attribute, when true, indicates the capability of the AP to provide
SSPN Interface service is enabled. The capability is disabled, otherwise.
The default value of this attribute is false."
DEFVAL {false}
::= { dot11StationConfigEntry 125 }
dot11HESSID OBJECT-TYPE
SYNTAX MacAddress
MAX-ACCESS read-write
STATUS current
DESCRIPTION
"This is a control variable.
It is written by an external management entity or the SME. Changes take
effect for the next MLME-START.request primitive.
This attribute is used by an AP and is the 6-octet homogeneous ESS identifier
field, whose value is set to one of the BSSIDs in the ESS. It is
required that the same value of HESSID be used for all BSSs in the homogeneous
ESS."
::= { dot11StationConfigEntry 126 }
dot11EASImplemented OBJECT-TYPE
SYNTAX TruthValue
MAX-ACCESS read-only
STATUS current
DESCRIPTION
"This is a capability variable.
Its value is determined by device capabilities.
This attribute when true, indicates the STA is capable of emergency alert
system notification with external networks. A STA setting this to true
implements emergency alert system notification. When this is false, the
STA does not implement emergency alert system notification."
DEFVAL {false}
::= { dot11StationConfigEntry 127 }
dot11EASActivated OBJECT-TYPE
SYNTAX TruthValue
MAX-ACCESS read-write
STATUS current
DESCRIPTION
"This is a control variable.
It is written by an external management entity or the SME. Changes take
effect as soon as practical in the implementation.
This attribute when true, indicates the STA is capable of supporting emergency
alert system. The capability is disabled otherwise."
DEFVAL {false}
::= { dot11StationConfigEntry 128 }
dot11MSGCFImplemented OBJECT-TYPE
SYNTAX TruthValue
MAX-ACCESS read-only
STATUS current
DESCRIPTION
"This is a capability variable.
Its value is determined by device capabilities.
This attribute when true, indicates the non-AP STA is capable of supporting
the MSGCF procedures defined in 6.4. When false, the non-AP STA does
not implement MSGCF procedures. This object is not used by APs. The
default value of this attribute is false."
DEFVAL {false}
::= { dot11StationConfigEntry 129 }
dot11MSGCFActivated OBJECT-TYPE
SYNTAX TruthValue
MAX-ACCESS read-write
STATUS current
DESCRIPTION
"This is a control variable.
It is written by an external management entity or the SME. Changes take
effect as soon as practical in the implementation.
This attribute, when true, indicates the capability of the non-AP STA to
provide the MSGCF is enabled. The capability is disabled, otherwise. The
default value of this attribute is false."
DEFVAL {false}
::= { dot11StationConfigEntry 130 }
dot11TimeAdvertisementTimeError OBJECT-TYPE
SYNTAX OCTET STRING (SIZE(5))
MAX-ACCESS read-write
STATUS current
DESCRIPTION
"This is a control variable.
It is written by an external management entity or the SME.
Changes take effect as soon as practical in the implementation.
This attribute indicates the Time Error value as defined in the Time
Advertisement element Time Error field when the Time Capabilities field is
set to 2. This field is included in the Time Advertisement element in Beacon
and Probe Response frames."
DEFVAL { ''H }
::= { dot11StationConfigEntry 131 }
dot11TimeAdvertisementTimeValue OBJECT-TYPE
SYNTAX OCTET STRING (SIZE(10))
MAX-ACCESS read-write
STATUS current
DESCRIPTION
"This is a control variable.
It is written by an external management entity or the SME.
Changes take effect as soon as practical in the implementation.
This attribute indicates the TimeAdvertisement Time Value as defined in
the Time Advertisement element Time Value field when the Time Capabilities
field is set to 2. The format is defined in Table 8-132 and is included in
the Time Advertisement element in Beacon and Probe Response frames."
::= { dot11StationConfigEntry 132 }
dot11RM3rdPartyMeasurementActivated OBJECT-TYPE
SYNTAX TruthValue
MAX-ACCESS read-write
STATUS current
DESCRIPTION
"This is a control variable.
It is written by an external management entity or the SME.
Changes take effect as soon as practical in the implementation.
This attribute, when true, indicates that dot11RadioMeasurementActivated
is true and that the station capability for Third Party Location Measurement
is enabled. False indicates the station has no Third Party Location
Measurement capability or that the capability is present but is disabled."
DEFVAL { false }
::= { dot11StationConfigEntry 133 }
dot11RejectUnadmittedTraffic OBJECT-TYPE
SYNTAX TruthValue
MAX-ACCESS read-write
STATUS current
DESCRIPTION
"This is a control variable.
It is written by an external management entity.
Changes take effect at the next MLME-START.request primitive or MLMEJOIN.
request primitive.
This attribute when true indicates the STA's MA-UNITDATA primitive rejects
frames whose requested priority corresponds to an AC for which admission
control is mandatory and for which there is not an admitted TSPEC."
DEFVAL { false }
::= {dot11StationConfigEntry 134}
dot11BSSBroadcastNullCount OBJECT-TYPE
SYNTAX Unsigned32 (1..64)
MAX-ACCESS read-write
STATUS current
DESCRIPTION
"This is a control variable.
It is written by an external management entity.
Changes take effect as soon as practical in the implementation.
This attribute specifies the number of group addressed Null data frames a
STA may transmit before it changes power management modes."
DEFVAL { 3 }
::= {dot11StationConfigEntry 135}
dot11MeshActivated OBJECT-TYPE
SYNTAX TruthValue
MAX-ACCESS read-write
STATUS current
DESCRIPTION
"This is a control variable.
It is written by an external management entity.
Changes take effect as soon as practical in the implementation.
When this object is true, this indicates that the STA is a mesh STA. Configuration
variables for mesh operation are found in the
dot11MeshSTAConfigTable."
::= { dot11StationConfigEntry 136 }
-- **********************************************************************
-- * End of dot11StationConfig TABLE
-- **********************************************************************
-- **********************************************************************
-- * dot11AuthenticationAlgorithms TABLE
-- **********************************************************************
dot11AuthenticationAlgorithmsTable OBJECT-TYPE
SYNTAX SEQUENCE OF Dot11AuthenticationAlgorithmsEntry
MAX-ACCESS not-accessible
STATUS current
DESCRIPTION
"This (conceptual) table of attributes is a set of all the authentication
algorithms supported by the stations. The following are the default values
and the associated algorithm:
Value = 1: Open System
Value = 2: Shared Key
Value = 3: Fast BSS Transition (FT)
Value = 4: Simultaneous authentication of equals (SAE)"
REFERENCE
"IEEE Std 802.11-2012, 8.4.1.1"
::= { dot11smt 2 }
dot11AuthenticationAlgorithmsEntry OBJECT-TYPE
SYNTAX Dot11AuthenticationAlgorithmsEntry
MAX-ACCESS not-accessible
STATUS current
DESCRIPTION
"An Entry (conceptual row) in the Authentication Algorithms Table.
ifIndex - Each IEEE 802.11 interface is represented by an ifEntry. Interface
tables in this MIB module are indexed by ifIndex."
INDEX { ifIndex,
dot11AuthenticationAlgorithmsIndex }
::= { dot11AuthenticationAlgorithmsTable 1 }
Dot11AuthenticationAlgorithmsEntry ::=
SEQUENCE {
dot11AuthenticationAlgorithmsIndex Unsigned32,
dot11AuthenticationAlgorithm INTEGER,
dot11AuthenticationAlgorithmsActivated TruthValue }
dot11AuthenticationAlgorithmsIndex OBJECT-TYPE
SYNTAX Unsigned32
MAX-ACCESS not-accessible
STATUS current
DESCRIPTION
"The auxiliary variable used to identify instances of the columnar objects
in the Authentication Algorithms Table."
::= { dot11AuthenticationAlgorithmsEntry 1 }
dot11AuthenticationAlgorithm OBJECT-TYPE
SYNTAX INTEGER {
openSystem(1),
sharedKey(2),
fastBSSTransition(3),
simultaneousAuthEquals(4) }
MAX-ACCESS read-only
STATUS current
DESCRIPTION
"This is a control variable.
It is written by an external management entity.
Changes take effect as soon as practical in the implementation.
This attribute is the authentication algorithm described by this entry in
the table. The following values can be used here
Value = 1: Open System
Value = 2: Shared Key
Value = 3: Fast BSS Transition (FT)
Value = 4: Simultaneous authentication of equals (SAE)"
::= { dot11AuthenticationAlgorithmsEntry 2 }
dot11AuthenticationAlgorithmsActivated OBJECT-TYPE
SYNTAX TruthValue
MAX-ACCESS read-write
STATUS current
DESCRIPTION
"This is a control variable.
It is written by an external management entity.
Changes take effect as soon as practical in the implementation.
This attribute, when true at a station, enables the acceptance of the
authentication algorithm described in the corresponding table entry in
authentication frames received by the station that have odd authentication
sequence numbers. The default value of this attribute is true when the
value of dot11AuthenticationAlgorithm is Open System and false otherwise."
::= { dot11AuthenticationAlgorithmsEntry 3 }
-- **********************************************************************
-- * End of dot11AuthenticationAlgorithms TABLE
-- **********************************************************************
-- **********************************************************************
-- * dot11WEPDefaultKeys TABLE
-- **********************************************************************
dot11WEPDefaultKeysTable OBJECT-TYPE
SYNTAX SEQUENCE OF Dot11WEPDefaultKeysEntry
MAX-ACCESS not-accessible
STATUS current
DESCRIPTION
"Conceptual table for WEP default keys. This table contains the four WEP
default secret key values corresponding to the four possible KeyID values.
The WEP default secret keys are logically WRITE-ONLY. Attempts to read the
entries in this table return unsuccessful status and values of null or 0.
The default value of each WEP default key is null."
REFERENCE "IEEE Std 802.11-2012, 11.2.2"
::= { dot11smt 3 }
dot11WEPDefaultKeysEntry OBJECT-TYPE
SYNTAX Dot11WEPDefaultKeysEntry
MAX-ACCESS not-accessible
STATUS current
DESCRIPTION
"An Entry (conceptual row) in the WEP Default Keys Table.
ifIndex - Each IEEE 802.11 interface is represented by an ifEntry. Interface
tables in this MIB module are indexed by ifIndex."
INDEX { ifIndex, dot11WEPDefaultKeyIndex }
::= { dot11WEPDefaultKeysTable 1 }
Dot11WEPDefaultKeysEntry ::=
SEQUENCE {
dot11WEPDefaultKeyIndex Unsigned32,
dot11WEPDefaultKeyValue WEPKeytype }
dot11WEPDefaultKeyIndex OBJECT-TYPE
SYNTAX Unsigned32 (1..4)
MAX-ACCESS not-accessible
STATUS current
DESCRIPTION
"The auxiliary variable used to identify instances of the columnar objects
in the WEP Default Keys Table. The value of this variable is equal to the
WEPDefaultKeyID + 1"
::= { dot11WEPDefaultKeysEntry 1 }
dot11WEPDefaultKeyValue OBJECT-TYPE
SYNTAX WEPKeytype
MAX-ACCESS read-write
STATUS current
DESCRIPTION
"This is a control variable.
It is written by an external management entity.
Changes take effect as soon as practical in the implementation.
A WEP default secret key value."
::= { dot11WEPDefaultKeysEntry 2 }
-- **********************************************************************
-- * End of dot11WEPDefaultKeys TABLE
-- **********************************************************************
-- **********************************************************************
-- * dot11WEPKeyMappings TABLE
-- **********************************************************************
dot11WEPKeyMappingsTable OBJECT-TYPE
SYNTAX SEQUENCE OF Dot11WEPKeyMappingsEntry
MAX-ACCESS not-accessible
STATUS current
DESCRIPTION
"Conceptual table for WEP Key Mappings. The MIB supports the ability to
share a separate WEP key for each RA/TA pair. The Key Mappings Table contains
zero or one entry for each MAC address and contains two fields for
each entry: WEPOn and the corresponding WEP key. The WEP key mappings are
logically WRITE-ONLY. Attempts to read the entries in this table return
unsuccessful status and values of null or 0. The default value for all
WEPOn fields is false."
REFERENCE "IEEE Std 802.11-2012, 11.2.2"
::= { dot11smt 4 }
dot11WEPKeyMappingsEntry OBJECT-TYPE
SYNTAX Dot11WEPKeyMappingsEntry
MAX-ACCESS not-accessible
STATUS current
DESCRIPTION
"An Entry (conceptual row) in the WEP Key Mappings Table.
ifIndex - Each IEEE 802.11 interface is represented by an ifEntry. Interface
tables in this MIB module are indexed by ifIndex."
INDEX { ifIndex, dot11WEPKeyMappingIndex }
::= { dot11WEPKeyMappingsTable 1 }
Dot11WEPKeyMappingsEntry ::=
SEQUENCE {
dot11WEPKeyMappingIndex Unsigned32,
dot11WEPKeyMappingAddress MacAddress,
dot11WEPKeyMappingWEPOn TruthValue,
dot11WEPKeyMappingValue WEPKeytype,
dot11WEPKeyMappingStatus RowStatus }
dot11WEPKeyMappingIndex OBJECT-TYPE
SYNTAX Unsigned32
MAX-ACCESS not-accessible
STATUS current
DESCRIPTION
"The auxiliary variable used to identify instances of the columnar objects
in the WEP Key Mappings Table."
::= { dot11WEPKeyMappingsEntry 1 }
dot11WEPKeyMappingAddress OBJECT-TYPE
SYNTAX MacAddress
MAX-ACCESS read-create
STATUS current
DESCRIPTION
"The MAC address of the STA for which the values from this key mapping
entry are to be used."
::= { dot11WEPKeyMappingsEntry 2 }
dot11WEPKeyMappingWEPOn OBJECT-TYPE
SYNTAX TruthValue
MAX-ACCESS read-create
STATUS current
DESCRIPTION
"Boolean as to whether WEP is to be used when communicating with the
dot11WEPKeyMappingAddress STA."
::= { dot11WEPKeyMappingsEntry 3 }
dot11WEPKeyMappingValue OBJECT-TYPE
SYNTAX WEPKeytype
MAX-ACCESS read-create
STATUS current
DESCRIPTION
"A WEP secret key value."
::= { dot11WEPKeyMappingsEntry 4 }
dot11WEPKeyMappingStatus OBJECT-TYPE
SYNTAX RowStatus
MAX-ACCESS read-create
STATUS current
DESCRIPTION
"The status column used for creating, modifying, and deleting instances of
the columnar objects in the WEP key mapping Table."
DEFVAL { active }
::= { dot11WEPKeyMappingsEntry 5 }
-- **********************************************************************
-- * End of dot11WEPKeyMappings TABLE
-- **********************************************************************
-- **********************************************************************
-- * dot11Privacy TABLE
-- **********************************************************************
dot11PrivacyTable OBJECT-TYPE
SYNTAX SEQUENCE OF Dot11PrivacyEntry
MAX-ACCESS not-accessible
STATUS current
DESCRIPTION
"Group containing attributes concerned with IEEE 802.11 Privacy. Created
as a table to allow multiple instantiations on an agent."
::= { dot11smt 5 }
dot11PrivacyEntry OBJECT-TYPE
SYNTAX Dot11PrivacyEntry
MAX-ACCESS not-accessible
STATUS current
DESCRIPTION
"An entry in the dot11PrivacyTable Table.
ifIndex - Each IEEE 802.11 interface is represented by an ifEntry. Interface
tables in this MIB module are indexed by ifIndex."
INDEX { ifIndex }
::= { dot11PrivacyTable 1 }
Dot11PrivacyEntry ::=
SEQUENCE {
dot11PrivacyInvoked TruthValue,
dot11WEPDefaultKeyID Unsigned32,
dot11WEPKeyMappingLengthImplemented Unsigned32,
dot11ExcludeUnencrypted TruthValue,
dot11WEPICVErrorCount Counter32,
dot11WEPExcludedCount Counter32,
dot11RSNAActivated TruthValue,
dot11RSNAPreauthenticationActivated TruthValue }
dot11PrivacyInvoked OBJECT-TYPE
SYNTAX TruthValue
MAX-ACCESS read-write
STATUS current
DESCRIPTION
"This is a control variable.
It is written by an external management entity.
Changes take effect as soon as practical in the implementation.
When this attribute is true, it indicates that some level of security is
invoked for transmitting data frames. For WEP-only clients, the security
mechanism used is WEP.
For RSNA-capable clients, an additional variable dot11RSNAActivated indicates
whether RSNA is enabled. If dot11RSNAActivated is false or the MIB
variable does not exist, the security mechanism invoked is WEP; if
dot11RSNAActivated is true, RSNA security mechanisms invoked are configured
in the dot11RSNAConfigTable."
DEFVAL { false }
::= { dot11PrivacyEntry 1 }
dot11WEPDefaultKeyID OBJECT-TYPE
SYNTAX Unsigned32 (0..3)
MAX-ACCESS read-write
STATUS current
DESCRIPTION
"This is a control variable.
It is written by an external management entity.
Changes take effect as soon as practical in the implementation.
This attribute indicates the use of the first, second, third, or fourth
element of the WEPDefaultKeys array when equal to values of zero, one,
two, or three."
REFERENCE "IEEE Std 802.11-2012, 11.2.2"
DEFVAL { 0 }
::= { dot11PrivacyEntry 2 }
dot11WEPKeyMappingLengthImplemented OBJECT-TYPE
SYNTAX Unsigned32 (10..4294967295)
MAX-ACCESS read-only
STATUS current
DESCRIPTION
"This is a capability variable.
Its value is determined by device capabilities.
The maximum number of tuples that dot11WEPKeyMappings can hold."
REFERENCE "IEEE Std 802.11-2012, 11.2.2"
::= { dot11PrivacyEntry 3 }
dot11ExcludeUnencrypted OBJECT-TYPE
SYNTAX TruthValue
MAX-ACCESS read-write
STATUS current
DESCRIPTION
"This is a control variable.
It is written by an external management entity.
Changes take effect as soon as practical in the implementation.
When this attribute is true, the STA does not indicate at the MAC service
interface received MSDUs that have the Protected Frame subfield of the
Frame Control field equal to 0. When this attribute is false, the STA may
accept MSDUs that have the Protected Frame subfield of the Frame Control
field equal to 0."
DEFVAL { false }
::= { dot11PrivacyEntry 4 }
dot11WEPICVErrorCount OBJECT-TYPE
SYNTAX Counter32
MAX-ACCESS read-only
STATUS current
DESCRIPTION
"This is a status variable.
It is written by the MAC when an ICV error is detected.
This counter increments when a frame is received with the Protected Frame
subfield of the Frame Control field equal to one and the value of the ICV
as received in the frame does not match the ICV value that is calculated
for the contents of the received frame. ICV errors for TKIP are not
counted in this variable but in dot11RSNAStatsTKIPICVErrors."
::= { dot11PrivacyEntry 5 }
dot11WEPExcludedCount OBJECT-TYPE
SYNTAX Counter32
MAX-ACCESS read-only
STATUS current
DESCRIPTION
"This is a status variable.
It is written by the MAC when a bad frame is received.
This counter increments when a frame is received with the Protected Frame
subfield of the Frame Control field equal to 0 and the value of
dot11ExcludeUnencrypted causes that frame to be discarded."
::= { dot11PrivacyEntry 6 }
dot11RSNAActivated OBJECT-TYPE
SYNTAX TruthValue
MAX-ACCESS read-write
STATUS current
DESCRIPTION
"This is a control variable.
It is written by an external management entity.
Changes take effect for the next MLME-START.request primitive or MLMEJOIN.
request primitive.
When this object is true, this indicates that RSNA is enabled on this
entity. The entity advertises the RSN element in its Beacon and Probe
Response frames. Configuration variables for RSNA operation are found in
the dot11RSNAConfigTable.
This object requires that dot11PrivacyInvoked also be equal to true."
::= { dot11PrivacyEntry 7 }
dot11RSNAPreauthenticationActivated OBJECT-TYPE
SYNTAX TruthValue
MAX-ACCESS read-write
STATUS current
DESCRIPTION
"This is a control variable.
It is written by an external management entity.
Changes take effect as soon as practical in the implementation.
When this object is true, this indicates that RSNA preauthentication is
enabled on this entity.
This object requires that dot11RSNAActivated also be equal to true."
::= { dot11PrivacyEntry 8 }
-- **********************************************************************
-- * End of dot11Privacy TABLE
-- **********************************************************************
-- **********************************************************************
-- * dot11SMTnotification Objects
-- **********************************************************************
dot11SMTnotification OBJECT IDENTIFIER ::= { dot11smt 6 }
dot11Disassociate NOTIFICATION-TYPE
OBJECTS { ifIndex, dot11DisassociateReason, dot11DisassociateStation }
STATUS current
DESCRIPTION
"The disassociate notification is sent when the STA sends a Disassociation
frame. The value of the notification includes the MAC address of the MAC
to which the Disassociation frame was sent and the reason for the disassociation.
ifIndex - Each IEEE 802.11 interface is represented by an ifEntry. Interface
tables in this MIB module are indexed by ifIndex."
::= { dot11SMTnotification 0 1 }
dot11Deauthenticate NOTIFICATION-TYPE
OBJECTS { ifIndex, dot11DeauthenticateReason, dot11DeauthenticateStation }
STATUS current
DESCRIPTION
"The deauthenticate notification is sent when the STA sends a Deauthentication
frame. The value of the notification includes the MAC address of
the MAC to which the Deauthentication frame was sent and the reason for
the deauthentication.
ifIndex - Each IEEE 802.11 interface is represented by an ifEntry. Interface
tables in this MIB module are indexed by ifIndex."
::= { dot11SMTnotification 0 2 }
dot11AuthenticateFail NOTIFICATION-TYPE
OBJECTS {
ifIndex, dot11AuthenticateFailStatus, dot11AuthenticateFailStation }
STATUS current
DESCRIPTION
"The authenticate failure notification is sent when the STA sends an
Authentication frame with a status code other than 'successful'. The value
of the notification includes the MAC address of the MAC to which the
Authentication frame was sent and the reason for the authentication failure.
ifIndex - Each IEEE 802.11 interface is represented by an ifEntry. Interface
tables in this MIB module are indexed by ifIndex."
::= { dot11SMTnotification 0 3 }
dot11Associate NOTIFICATION-TYPE
OBJECTS { ifIndex, dot11AssociateStation, dot11AssociateID}
STATUS current
DESCRIPTION
"The associate notification is sent when the STA sends an Association
Response frame with a status code equal to 'successful'. The value of the
notification includes the MAC address of the MAC to which the Association
Response frame was sent and the Association ID. ifIndex - Each 802.11
interface is represented by an ifEntry. Interface tables in this MIB module
are indexed by ifIndex."
::= { dot11SMTnotification 0 4 }
dot11AssociateFailed NOTIFICATION-TYPE
OBJECTS { ifIndex, dot11AssociateFailStatus, dot11AssociateFailStation }
STATUS current
DESCRIPTION
"The associate failed notification is sent when the STA sends an Association
Response frame with a status code other than 'successful'. The value
of the notification includes the MAC address of the MAC to which the Association
Response frame was sent and the reason for the association failure.
ifIndex - Each 802.11 interface is represented by an ifEntry.
Interface tables in this MIB module are indexed by ifIndex."
::= { dot11SMTnotification 0 5 }
dot11Reassociate NOTIFICATION-TYPE
OBJECTS { ifIndex, dot11ReassociateStation, dot11ReassociateID}
STATUS current
DESCRIPTION
"The reassociate notification is sent when the STA sends an Reassociation
Response frame with a status code equal to 'successful'. The value of the
notification includes the MAC address of the MAC to which the Reassociation
Response frame was sent and the Reassociation ID. ifIndex - Each
802.11 interface is represented by an ifEntry. Interface tables in this
MIB module are indexed by ifIndex."
::= { dot11SMTnotification 0 6 }
dot11ReassociateFailed NOTIFICATION-TYPE
OBJECTS { ifIndex, dot11ReassociateFailStatus, dot11ReassociateStation }
STATUS current
DESCRIPTION
"The reassociate failed notification is sent when the STA sends an Reassociation
Response frame with a status code other than 'successful'. The
value of the notification includes the MAC address of the MAC to which the
Reassociation Response frame was sent and the reason for the reassociation
failure. ifIndex - Each 802.11 interface is represented by an ifEntry.
Interface tables in this MIB module are indexed by ifIndex."
::= { dot11SMTnotification 0 7 }
-- **********************************************************************
-- * End of dot11SMTnotification Objects
-- **********************************************************************
-- **********************************************************************
-- * dot11MultiDomainCapability TABLE
-- **********************************************************************
dot11MultiDomainCapabilityTable OBJECT-TYPE
SYNTAX SEQUENCE OF Dot11MultiDomainCapabilityEntry
MAX-ACCESS not-accessible
STATUS current
DESCRIPTION
"This (conceptual) table of attributes for cross-domain mobility."
::= { dot11smt 7 }
dot11MultiDomainCapabilityEntry OBJECT-TYPE
SYNTAX Dot11MultiDomainCapabilityEntry
MAX-ACCESS not-accessible
STATUS current
DESCRIPTION
"An entry (conceptual row) in the Multiple Domain Capability Table.
IfIndex - Each IEEE 802.11 interface is represented by an ifEntry. Interface
tables in this MIB are indexed by ifIndex."
INDEX { ifIndex, dot11MultiDomainCapabilityIndex }
::= { dot11MultiDomainCapabilityTable 1 }
Dot11MultiDomainCapabilityEntry ::=
SEQUENCE {
dot11MultiDomainCapabilityIndex Unsigned32,
dot11FirstChannelNumber Unsigned32,
dot11NumberofChannels Unsigned32,
dot11MaximumTransmitPowerLevel Integer32 }
dot11MultiDomainCapabilityIndex OBJECT-TYPE
SYNTAX Unsigned32
MAX-ACCESS not-accessible
STATUS current
DESCRIPTION
"The auxiliary variable used to identify instances of the columnar objects
in the Multi Domain Capability Table."
::= { dot11MultiDomainCapabilityEntry 1 }
dot11FirstChannelNumber OBJECT-TYPE
SYNTAX Unsigned32
MAX-ACCESS read-write
STATUS current
DESCRIPTION
"This is a control variable.
It is written by an external management entity.
Changes take effect as soon as practical in the implementation.
This attribute indicates the value of the lowest channel number in the
subband for the associated domain country string."
DEFVAL { 0 }
::= { dot11MultiDomainCapabilityEntry 2 }
dot11NumberofChannels OBJECT-TYPE
SYNTAX Unsigned32
MAX-ACCESS read-write
STATUS current
DESCRIPTION
"This is a control variable.
It is written by an external management entity.
Changes take effect as soon as practical in the implementation.
This attribute indicates the value of the total number of channels allowed
in the subband for the associated domain country string."
DEFVAL { 0 }
::= { dot11MultiDomainCapabilityEntry 3 }
dot11MaximumTransmitPowerLevel OBJECT-TYPE
SYNTAX Integer32
MAX-ACCESS read-write
STATUS current
DESCRIPTION
"This is a control variable.
It is written by an external management entity.
Changes take effect as soon as practical in the implementation.
This attribute indicates the maximum transmit power, in dBm, allowed in
the subband for the associated domain country string."
DEFVAL { 0 }
::= { dot11MultiDomainCapabilityEntry 4 }
-- ********************************************************************
-- * End of dot11MultiDomainCapability TABLE
-- ********************************************************************
-- ********************************************************************
-- * dot11SpectrumManagement TABLE
-- ********************************************************************
dot11SpectrumManagementTable OBJECT-TYPE
SYNTAX SEQUENCE OF Dot11SpectrumManagementEntry
MAX-ACCESS not-accessible
STATUS current
DESCRIPTION
"(Conceptual) table of attributes for spectrum management"
::= {dot11smt 8}
dot11SpectrumManagementEntry OBJECT-TYPE
SYNTAX Dot11SpectrumManagementEntry
MAX-ACCESS not-accessible
STATUS current
DESCRIPTION
"An entry (conceptual row) in the Spectrum Management Table.
IfIndex - Each 802.11 interface is represented by an ifEntry. Interface
tables in this MIB are indexed by ifIndex."
INDEX {ifIndex, dot11SpectrumManagementIndex}
::= { dot11SpectrumManagementTable 1 }
Dot11SpectrumManagementEntry ::=
SEQUENCE {
dot11SpectrumManagementIndex Unsigned32,
dot11MitigationRequirement Integer32,
dot11ChannelSwitchTime Unsigned32,
dot11PowerCapabilityMaxImplemented Integer32,
dot11PowerCapabilityMinImplemented Integer32 }
dot11SpectrumManagementIndex OBJECT-TYPE
SYNTAX Unsigned32
MAX-ACCESS not-accessible
STATUS current
DESCRIPTION
"The auxiliary variable used to identify instances of the columnar objects
in the Spectrum Management Table."
::= { dot11SpectrumManagementEntry 1 }
dot11MitigationRequirement OBJECT-TYPE
SYNTAX Integer32
MAX-ACCESS read-write
STATUS current
DESCRIPTION
"This is a control variable.
It is written by an external management entity.
Changes take effect as soon as practical in the implementation.
This attribute indicates the mitigation requirement in dB required."
DEFVAL { 3 }
::= { dot11SpectrumManagementEntry 2 }
dot11ChannelSwitchTime OBJECT-TYPE
SYNTAX Unsigned32
MAX-ACCESS read-write
STATUS current
DESCRIPTION
"This is a control variable.
It is written by an external management entity.
Changes take effect as soon as practical in the implementation.
This attribute indicates assumed channel switch time, measured in TUs. The
unit of this attribute is TUs. The minimum value of this attribute is 1
TU."
DEFVAL { 2 }
::= { dot11SpectrumManagementEntry 3 }
dot11PowerCapabilityMaxImplemented OBJECT-TYPE
SYNTAX Integer32
MAX-ACCESS read-only
STATUS current
DESCRIPTION
"This is a capability variable.
Its value is determined by device capabilities.
This attribute indicates the maximum transmit Power Capability of this
station. The unit of this attribute is dBm."
DEFVAL { 0 }
::= { dot11SpectrumManagementEntry 4 }
dot11PowerCapabilityMinImplemented OBJECT-TYPE
SYNTAX Integer32
MAX-ACCESS read-only
STATUS current
DESCRIPTION
"This is a capability variable.
Its value is determined by device capabilities.
This attribute indicates the minimum transmit Power Capability of this
station. The unit of this attribute is dBm."
DEFVAL { -100 }
::= { dot11SpectrumManagementEntry 5 }
-- ******************************************************************
-- * End of dot11SpectrumManagement TABLE
-- ******************************************************************
-- ********************************************************************
-- * dot11RSNAConfig TABLE (RSNA and TSN)
-- ********************************************************************
dot11RSNAConfigTable OBJECT-TYPE
SYNTAX SEQUENCE OF Dot11RSNAConfigEntry
MAX-ACCESS not-accessible
STATUS current
DESCRIPTION
"The table containing RSNA configuration objects."
::= { dot11smt 9 }
dot11RSNAConfigEntry OBJECT-TYPE
SYNTAX Dot11RSNAConfigEntry
MAX-ACCESS not-accessible
STATUS current
DESCRIPTION
"An entry in the dot11RSNAConfigTable."
INDEX { ifIndex }
::= { dot11RSNAConfigTable 1 }
Dot11RSNAConfigEntry ::=
SEQUENCE {
dot11RSNAConfigVersion Unsigned32,
dot11RSNAConfigPairwiseKeysImplemented Unsigned32,
dot11RSNAConfigGroupCipher OCTET STRING,
dot11RSNAConfigGroupRekeyMethod INTEGER,
dot11RSNAConfigGroupRekeyTime Unsigned32,
dot11RSNAConfigGroupRekeyPackets Unsigned32,
dot11RSNAConfigGroupRekeyStrict TruthValue,
dot11RSNAConfigPSKValue OCTET STRING,
dot11RSNAConfigPSKPassPhrase DisplayString,
dot11RSNAConfigGroupUpdateCount Unsigned32,
dot11RSNAConfigPairwiseUpdateCount Unsigned32,
dot11RSNAConfigGroupCipherSize Unsigned32,
dot11RSNAConfigPMKLifetime Unsigned32,
dot11RSNAConfigPMKReauthThreshold Unsigned32,
dot11RSNAConfigNumberOfPTKSAReplayCountersImplemented
Unsigned32,
dot11RSNAConfigSATimeout Unsigned32,
dot11RSNAAuthenticationSuiteSelected OCTET STRING,
dot11RSNAPairwiseCipherSelected OCTET STRING,
dot11RSNAGroupCipherSelected OCTET STRING,
dot11RSNAPMKIDUsed OCTET STRING,
dot11RSNAAuthenticationSuiteRequested OCTET STRING,
dot11RSNAPairwiseCipherRequested OCTET STRING,
dot11RSNAGroupCipherRequested OCTET STRING,
dot11RSNATKIPCounterMeasuresInvoked Unsigned32,
dot11RSNA4WayHandshakeFailures Unsigned32,
dot11RSNAConfigNumberOfGTKSAReplayCountersImplemented
Unsigned32,
dot11RSNAConfigSTKKeysImplemented Unsigned32,
dot11RSNAConfigSTKCipher OCTET STRING,
dot11RSNAConfigSTKRekeyTime Unsigned32,
dot11RSNAConfigSMKUpdateCount Unsigned32,
dot11RSNAConfigSTKCipherSize Unsigned32,
dot11RSNAConfigSMKLifetime Unsigned32,
dot11RSNAConfigSMKReauthThreshold Unsigned32,
dot11RSNAConfigNumberOfSTKSAReplayCountersImplemented
Unsigned32,
dot11RSNAPairwiseSTKSelected OCTET STRING,
dot11RSNASMKHandshakeFailures Unsigned32,
dot11RSNASAERetransPeriod Unsigned32,
dot11RSNASAEAntiCloggingThreshold Unsigned32,
dot11RSNASAESync Unsigned32 }
-- dot11RSNAConfigEntry 1 has been deprecated.
dot11RSNAConfigVersion OBJECT-TYPE
SYNTAX Unsigned32
MAX-ACCESS read-only
STATUS current
DESCRIPTION
"This is a capability variable.
Its value is determined by device capabilities.
The highest RSNA version this entity supports. See 8.4.2.10."
::= { dot11RSNAConfigEntry 2 }
dot11RSNAConfigPairwiseKeysImplemented OBJECT-TYPE
SYNTAX Unsigned32
MAX-ACCESS read-only
STATUS current
DESCRIPTION
"This is a capability variable.
Its value is determined by device capabilities.
This object indicates how many pairwise keys the entity supports for
RSNA."
::= { dot11RSNAConfigEntry 3 }
dot11RSNAConfigGroupCipher OBJECT-TYPE
SYNTAX OCTET STRING (SIZE(4))
MAX-ACCESS read-write
STATUS current
DESCRIPTION
"This is a control variable.
It is written by an external management entity.
Changes take effect as soon as practical in the implementation.
This object indicates the group cipher suite selector the entity must use.
The group cipher suite in the RSN element takes its value from this variable. 
It consists of an OUI (the first 3 octets) and a cipher suite identifier
(the last octet)."
::= { dot11RSNAConfigEntry 4 }
dot11RSNAConfigGroupRekeyMethod OBJECT-TYPE
SYNTAX INTEGER { disabled(1), timeBased(2), packetBased(3),
timepacketBased(4) }
MAX-ACCESS read-write
STATUS current
DESCRIPTION
"This is a control variable.
It is written by an external management entity.
Changes take effect as soon as practical in the implementation.
This object selects a mechanism for rekeying the RSNA GTK. The default is
time-based, once per day. Rekeying the GTK is only applicable to an entity
acting in the Authenticator role (an AP in an ESS)."
DEFVAL { timeBased }
::= { dot11RSNAConfigEntry 5 }
dot11RSNAConfigGroupRekeyTime OBJECT-TYPE
SYNTAX Unsigned32 (1..4294967295)
UNITS "seconds"
MAX-ACCESS read-write
STATUS current
DESCRIPTION
"This is a control variable.
It is written by an external management entity.
Changes take effect as soon as practical in the implementation.
The time in seconds after which the RSNA GTK is refreshed. The timer
starts at the moment the GTK was set using the MLME-SETKEYS.request primitive."
DEFVAL { 86400 } -- once per day
::= { dot11RSNAConfigEntry 6 }
dot11RSNAConfigGroupRekeyPackets OBJECT-TYPE
SYNTAX Unsigned32 (1..4294967295)
UNITS "1000 packets"
MAX-ACCESS read-write
STATUS current
DESCRIPTION
"This is a control variable.
It is written by an external management entity.
Changes take effect as soon as practical in the implementation.
A packet count (in 1000s of packets) after which the RSNA GTK is
refreshed. The packet counter starts at the moment the GTK was set using
the MLME-SETKEYS.request primitive and it counts all packets encrypted
using the current GTK."
::= { dot11RSNAConfigEntry 7 }
dot11RSNAConfigGroupRekeyStrict OBJECT-TYPE
SYNTAX TruthValue
MAX-ACCESS read-write
STATUS current
DESCRIPTION
"This is a control variable.
It is written by an external management entity.
Changes take effect as soon as practical in the implementation.
This object signals that the GTK be refreshed whenever a STA leaves the
BSS that possesses the GTK."
::= { dot11RSNAConfigEntry 8 }
dot11RSNAConfigPSKValue OBJECT-TYPE
SYNTAX OCTET STRING (SIZE(32))
MAX-ACCESS read-write
STATUS current
DESCRIPTION
"This is a control variable.
It is written by an external management entity.
Changes take effect as soon as practical in the implementation.
The PSK for when RSNA in PSK mode is the selected AKM suite. In that case,
the PMK obtains its value from this object.
This object is logically write-only. Reading this variable returns unsuccessful
status or null or 0."
::= { dot11RSNAConfigEntry 9 }
dot11RSNAConfigPSKPassPhrase OBJECT-TYPE
SYNTAX DisplayString
MAX-ACCESS read-write
STATUS current
DESCRIPTION
"This is a control variable.
It is written by an external management entity.
Changes take effect as soon as practical in the implementation.
The PSK, for when RSNA in PSK mode is the selected AKM suite, is configured
by dot11RSNAConfigPSKValue.
An alternative manner of setting the PSK uses the password-to-key algorithm
defined in M.4. This variable provides a means to enter a passphrase.
When this object is written, the RSNA entity uses the password-tokey
algorithm specified in M.4 to derive a preshared and populate
dot11RSNAConfigPSKValue with this key.
This object is logically write-only. Reading this variable returns unsuccessful
status or null or 0."
::= { dot11RSNAConfigEntry 10 }
-- dot11RSNAConfigEntry 11 and dot11RSNAConfigEntry 12 have been
-- deprecated.
dot11RSNAConfigGroupUpdateCount OBJECT-TYPE
SYNTAX Unsigned32 (1..4294967295)
MAX-ACCESS read-write
STATUS current
DESCRIPTION
"This is a control variable.
It is written by an external management entity.
Changes take effect as soon as practical in the implementation.
The number of times Message 1 in the RSNA Group Key Handshake is retried
per GTK Handshake attempt."
DEFVAL { 3 }
::= { dot11RSNAConfigEntry 13 }
dot11RSNAConfigPairwiseUpdateCount OBJECT-TYPE
SYNTAX Unsigned32 (1..4294967295)
MAX-ACCESS read-write
STATUS current
DESCRIPTION
"This is a control variable.
It is written by an external management entity.
Changes take effect as soon as practical in the implementation.
The number of times Message 1 and Message 3 in the RSNA 4-Way Handshake is
retried per 4-Way Handshake attempt."
DEFVAL { 3 }
::= { dot11RSNAConfigEntry 14 }
dot11RSNAConfigGroupCipherSize OBJECT-TYPE
SYNTAX Unsigned32 (0..4294967295)
MAX-ACCESS read-write
STATUS current
DESCRIPTION
"This is a control variable.
It is written by an external management entity.
Changes take effect as soon as practical in the implementation.
This object indicates the length in bits of the group cipher key."
::= { dot11RSNAConfigEntry 15 }
dot11RSNAConfigPMKLifetime OBJECT-TYPE
SYNTAX Unsigned32 (1..4294967295)
UNITS "seconds"
MAX-ACCESS read-write
STATUS current
DESCRIPTION
"This is a control variable.
It is written by an external management entity.
Changes take effect as soon as practical in the implementation.
The maximum lifetime of a PMK in the PMK cache."
DEFVAL { 43200 }
::= { dot11RSNAConfigEntry 16 }
dot11RSNAConfigPMKReauthThreshold OBJECT-TYPE
SYNTAX Unsigned32 (1..100)
UNITS "percentage"
MAX-ACCESS read-write
STATUS current
DESCRIPTION
"This is a control variable.
It is written by an external management entity.
Changes take effect as soon as practical in the implementation.
The percentage of the PMK lifetime that should expire before an IEEE
802.1X reauthentication occurs."
DEFVAL { 70 }
::= { dot11RSNAConfigEntry 17 }
dot11RSNAConfigNumberOfPTKSAReplayCountersImplemented OBJECT-TYPE
SYNTAX Unsigned32
MAX-ACCESS read-only
STATUS current
DESCRIPTION
"This is a capability variable.
Its value is determined by device capabilities.
Specifies the number of PTKSA replay counters per association:
0 -> 1 replay counter,
1 -> 2 replay counters,
2 -> 4 replay counters,
3 -> 16 replay counters"
DEFVAL { 3 }
::= { dot11RSNAConfigEntry 18 }
dot11RSNAConfigSATimeout OBJECT-TYPE
SYNTAX Unsigned32 (1..4294967295)
UNITS "seconds"
MAX-ACCESS read-write
STATUS current
DESCRIPTION
"This is a control variable.
It is written by an external management entity.
Changes take effect as soon as practical in the implementation.
The maximum time a security association takes to set up."
DEFVAL { 60 }
::= { dot11RSNAConfigEntry 19 }
dot11RSNAAuthenticationSuiteSelected OBJECT-TYPE
SYNTAX OCTET STRING (SIZE(4))
MAX-ACCESS read-only
STATUS current
DESCRIPTION
"This is a status variable.
It is written by the RSNA Key Management in the SME when a security association
is established.
The selector of the last AKM suite negotiated."
::= { dot11RSNAConfigEntry 20 }
dot11RSNAPairwiseCipherSelected OBJECT-TYPE
SYNTAX OCTET STRING (SIZE(4))
MAX-ACCESS read-only
STATUS current
DESCRIPTION
"This is a status variable.
It is written by the RSNA Key Management in the SME when a security association
is established.
The selector of the last pairwise cipher negotiated."
::= { dot11RSNAConfigEntry 21 }
dot11RSNAGroupCipherSelected OBJECT-TYPE
SYNTAX OCTET STRING (SIZE(4))
MAX-ACCESS read-only
STATUS current
DESCRIPTION
"This is a status variable.
It is written by the RSNA Key Management in the SME when a security association
is established.
The selector of the last group cipher negotiated."
::= { dot11RSNAConfigEntry 22 }
dot11RSNAPMKIDUsed OBJECT-TYPE
SYNTAX OCTET STRING (SIZE(16))
MAX-ACCESS read-only
STATUS current
DESCRIPTION
"This is a status variable.
It is written by the RSNA Key Management in the SME when a security association
is established.
The selector of the last PMKID used in the last 4-Way Handshake."
::= { dot11RSNAConfigEntry 23 }
dot11RSNAAuthenticationSuiteRequested OBJECT-TYPE
SYNTAX OCTET STRING (SIZE(4))
MAX-ACCESS read-only
STATUS current
DESCRIPTION
"This is a status variable.
It is written by the RSNA Key Management in the SME when a security association
is established.
The selector of the last AKM suite requested."
::= { dot11RSNAConfigEntry 24 }
dot11RSNAPairwiseCipherRequested OBJECT-TYPE
SYNTAX OCTET STRING (SIZE(4))
MAX-ACCESS read-only
STATUS current
DESCRIPTION
"This is a status variable.
It is written by the RSNA Key Management in the SME when a security association
is established.
The selector of the last pairwise cipher requested."
::= { dot11RSNAConfigEntry 25 }
dot11RSNAGroupCipherRequested OBJECT-TYPE
SYNTAX OCTET STRING (SIZE(4))
MAX-ACCESS read-only
STATUS current
DESCRIPTION
"This is a status variable.
It is written by the RSNA Key Management in the SME when a security association
is established.
The selector of the last group cipher requested."
::= { dot11RSNAConfigEntry 26 }
dot11RSNATKIPCounterMeasuresInvoked OBJECT-TYPE
SYNTAX Unsigned32 (0..4294967295)
MAX-ACCESS read-only
STATUS current
DESCRIPTION
"This is a status variable.
It is written by the MAC when the condition described below occurs.
Counts the number of times that a TKIP MIC failure occurred two times
within 60 s and TKIP countermeasures were invoked. This attribute counts
both local and remote MIC failure events reported to this STA. It increments
every time TKIP countermeasures are invoked"
::= { dot11RSNAConfigEntry 27 }
dot11RSNA4WayHandshakeFailures OBJECT-TYPE
SYNTAX Unsigned32 (0..4294967295)
MAX-ACCESS read-only
STATUS current
DESCRIPTION
"This is a status variable.
It is written by the RSNA Key Management in the SME when the condition
described below occurs.
Counts the number of 4-Way Handshake failures."
::= { dot11RSNAConfigEntry 28 }
dot11RSNAConfigNumberOfGTKSAReplayCountersImplemented OBJECT-TYPE
SYNTAX Unsigned32
MAX-ACCESS read-only
STATUS current
DESCRIPTION
"This is a capability variable.
Its value is determined by device capabilities.
Specifies the number of GTKSA replay counters per association:
0 -> 1 replay counter,
1 -> 2 replay counters,
2 -> 4 replay counters,
3 -> 16 replay counters"
DEFVAL { 3 }
::= { dot11RSNAConfigEntry 29 }
dot11RSNAConfigSTKKeysImplemented OBJECT-TYPE
SYNTAX Unsigned32
MAX-ACCESS read-only
STATUS current
DESCRIPTION
"This is a capability variable.
Its value is determined by device capabilities.
This object indicates how many STK keys the entity supports for RSNA."
::= { dot11RSNAConfigEntry 30 }
dot11RSNAConfigSTKCipher OBJECT-TYPE
SYNTAX OCTET STRING (SIZE(4))
MAX-ACCESS read-write
STATUS current
DESCRIPTION
"This is a control variable.
It is written by an external management entity.
Changes take effect as soon as practical in the implementation.
This object specifies the ciphersuite used by the STK for a DLS link."
::= { dot11RSNAConfigEntry 31}
dot11RSNAConfigSTKRekeyTime OBJECT-TYPE
SYNTAX Unsigned32 (1..4294967295)
UNITS "seconds"
MAX-ACCESS read-write
STATUS current
DESCRIPTION
"This is a control variable.
It is written by an external management entity.
Changes take effect as soon as practical in the implementation.
The time in seconds after which an RSNA STK is refreshed. The timer starts
at the moment the STK was set using the MLME-SETKEYS.request primitive."
DEFVAL { 86400 } -- once per day
::= { dot11RSNAConfigEntry 32 }
dot11RSNAConfigSMKUpdateCount OBJECT-TYPE
SYNTAX Unsigned32 (1..4294967295)
MAX-ACCESS read-write
STATUS current
DESCRIPTION
"This is a control variable.
It is written by an external management entity.
Changes take effect as soon as practical in the implementation.
The number of times Message 1 in the RSNA SMK Handshake is retried per SMK
Handshake attempt."
DEFVAL { 3 }
::= { dot11RSNAConfigEntry 33 }
dot11RSNAConfigSTKCipherSize OBJECT-TYPE
SYNTAX Unsigned32 (0..4294967295)
MAX-ACCESS read-write
STATUS current
DESCRIPTION
"This is a control variable.
It is written by an external management entity.
Changes take effect as soon as practical in the implementation.
This object indicates the length in bits of the STK cipher key."
::= { dot11RSNAConfigEntry 34 }
dot11RSNAConfigSMKLifetime OBJECT-TYPE
SYNTAX Unsigned32 (1..4294967295)
UNITS "seconds"
MAX-ACCESS read-write
STATUS current
DESCRIPTION
"This is a control variable.
It is written by an external management entity.
Changes take effect as soon as practical in the implementation.
The maximum lifetime of an SMK in the SMK cache."
DEFVAL { 43200 }
::= { dot11RSNAConfigEntry 35 }
dot11RSNAConfigSMKReauthThreshold OBJECT-TYPE
SYNTAX Unsigned32 (0..4294967295)
MAX-ACCESS read-write
STATUS current
DESCRIPTION
"This is a control variable.
It is written by an external management entity.
Changes take effect as soon as practical in the implementation.
This attribute indicates the number of seconds for which an SMK authentication
is valid. A new SMK authentication must be completed successfully
before the number of seconds indicated by this attribute elapse, from the
prior authentication, before the STAs become unauthenticated."
::= { dot11RSNAConfigEntry 36 }
dot11RSNAConfigNumberOfSTKSAReplayCountersImplemented OBJECT-TYPE
SYNTAX Unsigned32
MAX-ACCESS read-only
STATUS current
DESCRIPTION
"This is a capability variable.
Its value is determined by device capabilities.
Specifies the number of STKSA replay counters per association:
0 -> 1 replay counter,
1 -> 2 replay counters,
2 -> 4 replay counters,
3 -> 16 replay counters"
DEFVAL { 3 }
::= { dot11RSNAConfigEntry 37 }
dot11RSNAPairwiseSTKSelected OBJECT-TYPE
SYNTAX OCTET STRING (SIZE(4))
MAX-ACCESS read-only
STATUS current
DESCRIPTION
"This is a status variable.
It is written by the RSNA Key Management in the SME when a security association
is established.
The selector of the last STK cipher negotiated."
::= { dot11RSNAConfigEntry 38 }
dot11RSNASMKHandshakeFailures OBJECT-TYPE
SYNTAX Unsigned32 (0..4294967295)
MAX-ACCESS read-only
STATUS current
DESCRIPTION
"This is a status variable.
It is written by the RSNA Key Management in the SME when the condition
described below occurs.
Counts the number of SMK Handshake failures."
::= { dot11RSNAConfigEntry 39 }
dot11RSNASAERetransPeriod OBJECT-TYPE
SYNTAX Unsigned32
MAX-ACCESS read-only
STATUS current
DESCRIPTION
"This is a control variable.
It is written by the SME when establishing or becoming a member of a BSS.
Changes take effect for the next MLME-START.request.
This object specifies the initial retry timeout, in millisecond units,
used by the SAE authentication and key establishment protocol."
DEFVAL { 40 }
::= { dot11RSNAConfigEntry 40 }
dot11RSNASAEAntiCloggingThreshold OBJECT-TYPE
SYNTAX Unsigned32
MAX-ACCESS read-only
STATUS current
DESCRIPTION
"This is a capability variable.
Its value is determined by device capabilities.
This object specifies the maximum number of SAE protocol instances allowed
to simultaneously be in either Commit or Confirmed state."
DEFVAL { 5 }
::= { dot11RSNAConfigEntry 41 }
dot11RSNASAESync OBJECT-TYPE
SYNTAX Unsigned32
MAX-ACCESS read-only
STATUS current
DESCRIPTION
"This is a capability variable.
Its value is determined by device capabilities.
This object specifies the maximum number of synchronization errors that
are allowed to happen prior to disassociation of the offending SAE peer."
DEFVAL { 5 }
::= { dot11RSNAConfigEntry 42 }
-- ********************************************************************
-- * End of dot11RSNAConfig TABLE
-- ********************************************************************
-- ********************************************************************
-- * dot11RSNAConfigPairwiseCiphers TABLE
-- ********************************************************************
dot11RSNAConfigPairwiseCiphersTable OBJECT-TYPE
SYNTAX SEQUENCE OF Dot11RSNAConfigPairwiseCiphersEntry
MAX-ACCESS not-accessible
STATUS current
DESCRIPTION
"This table lists the pairwise ciphers supported by this entity. It allows
enabling and disabling of each pairwise cipher by network management. The
pairwise cipher suite list in the RSNE is formed using the information in
this table."
::= { dot11smt 10 }
dot11RSNAConfigPairwiseCiphersEntry OBJECT-TYPE
SYNTAX Dot11RSNAConfigPairwiseCiphersEntry
MAX-ACCESS not-accessible
STATUS current
DESCRIPTION
"The table entry, indexed by the interface index (or all interfaces) and
the pairwise cipher."
INDEX { ifIndex, dot11RSNAConfigPairwiseCipherIndex }
::= { dot11RSNAConfigPairwiseCiphersTable 1 }
Dot11RSNAConfigPairwiseCiphersEntry ::=
SEQUENCE {
dot11RSNAConfigPairwiseCipherIndex Unsigned32,
dot11RSNAConfigPairwiseCipherImplemented OCTET STRING,
dot11RSNAConfigPairwiseCipherActivated TruthValue,
dot11RSNAConfigPairwiseCipherSizeImplemented Unsigned32 }
dot11RSNAConfigPairwiseCipherIndex OBJECT-TYPE
SYNTAX Unsigned32 (1..4294967295)
MAX-ACCESS not-accessible
STATUS current
DESCRIPTION
"The auxiliary index into the dot11RSNAConfigPairwiseCiphersTable."
::= { dot11RSNAConfigPairwiseCiphersEntry 1 }
dot11RSNAConfigPairwiseCipherImplemented OBJECT-TYPE
SYNTAX OCTET STRING (SIZE(4))
MAX-ACCESS read-only
STATUS current
DESCRIPTION
"This is a capability variable.
Its value is determined by device capabilities.
The selector of a supported pairwise cipher. It consists of an OUI (the
first 3 octets) and a cipher suite identifier (the last octet)."
::= { dot11RSNAConfigPairwiseCiphersEntry 2 }
dot11RSNAConfigPairwiseCipherActivated OBJECT-TYPE
SYNTAX TruthValue
MAX-ACCESS read-write
STATUS current
DESCRIPTION
"This is a control variable.
It is written by an external management entity.
Changes take effect as soon as practical in the implementation.
This object enables or disables the pairwise cipher."
::= { dot11RSNAConfigPairwiseCiphersEntry 3 }
dot11RSNAConfigPairwiseCipherSizeImplemented OBJECT-TYPE
SYNTAX Unsigned32 (0..4294967295)
MAX-ACCESS read-only
STATUS current
DESCRIPTION
"This is a capability variable.
Its value is determined by device capabilities.
This object indicates the length in bits of the pairwise cipher key. This
should be 256 for TKIP and 128 for CCMP."
::= { dot11RSNAConfigPairwiseCiphersEntry 4 }
-- ********************************************************************
-- * End of dot11RSNAConfigPairwiseCiphers TABLE
-- ********************************************************************
-- ********************************************************************
-- * dot11RSNAConfigAuthenticationSuites TABLE
-- ********************************************************************
dot11RSNAConfigAuthenticationSuitesTable OBJECT-TYPE
SYNTAX SEQUENCE OF Dot11RSNAConfigAuthenticationSuitesEntry
MAX-ACCESS not-accessible
STATUS current
DESCRIPTION
"This table lists the AKM suites supported by this entity. Each AKM suite
can be individually enabled and disabled. The AKM suite list in the RSNE
is formed using the information in this table."
::= { dot11smt 11 }
dot11RSNAConfigAuthenticationSuitesEntry OBJECT-TYPE
SYNTAX Dot11RSNAConfigAuthenticationSuitesEntry
MAX-ACCESS not-accessible
STATUS current
DESCRIPTION
"An entry (row) in the dot11RSNAConfigAuthenticationSuitesTable."
INDEX { dot11RSNAConfigAuthenticationSuiteIndex }
::= { dot11RSNAConfigAuthenticationSuitesTable 1 }
Dot11RSNAConfigAuthenticationSuitesEntry ::=
SEQUENCE {
dot11RSNAConfigAuthenticationSuiteIndex Unsigned32,
dot11RSNAConfigAuthenticationSuiteImplemented OCTET STRING,
dot11RSNAConfigAuthenticationSuiteActivated TruthValue }
dot11RSNAConfigAuthenticationSuiteIndex OBJECT-TYPE
SYNTAX Unsigned32 (1..4294967295)
MAX-ACCESS not-accessible
STATUS current
DESCRIPTION
"The auxiliary variable used as an index into the
dot11RSNAConfigAuthenticationSuitesTable."
::= { dot11RSNAConfigAuthenticationSuitesEntry 1 }
dot11RSNAConfigAuthenticationSuiteImplemented OBJECT-TYPE
SYNTAX OCTET STRING (SIZE(4))
MAX-ACCESS read-only
STATUS current
DESCRIPTION
"This is a capability variable.
Its value is determined by device capabilities.
The selector of an AKM suite. It consists of an OUI (the first 3 octets)
and a cipher suite identifier (the last octet)."
::= { dot11RSNAConfigAuthenticationSuitesEntry 2 }
dot11RSNAConfigAuthenticationSuiteActivated OBJECT-TYPE
SYNTAX TruthValue
MAX-ACCESS read-write
STATUS current
DESCRIPTION
"This is a control variable.
It is written by an external management entity.
Changes take effect as soon as practical in the implementation.
This variable indicates whether the corresponding AKM suite is enabled/
disabled."
::= { dot11RSNAConfigAuthenticationSuitesEntry 3 }
-- ********************************************************************
-- * End of dot11RSNAConfigAuthenticationSuites TABLE
-- ********************************************************************
-- ********************************************************************
-- * dot11RSNAStats TABLE
-- ********************************************************************
dot11RSNAStatsTable OBJECT-TYPE
SYNTAX SEQUENCE OF Dot11RSNAStatsEntry
MAX-ACCESS not-accessible
STATUS current
DESCRIPTION
"This table maintains per-STA statistics in an RSN. The entry with
dot11RSNAStatsSTAAddress equal to FF-FF-FF-FF-FF-FF contains statistics
for group addressed traffic."
::= { dot11smt 12 }
dot11RSNAStatsEntry OBJECT-TYPE
SYNTAX Dot11RSNAStatsEntry
MAX-ACCESS not-accessible
STATUS current
DESCRIPTION
"An entry in the dot11RSNAStatsTable."
INDEX { ifIndex, dot11RSNAStatsIndex }
::= { dot11RSNAStatsTable 1 }
Dot11RSNAStatsEntry ::=
SEQUENCE {
dot11RSNAStatsIndex Unsigned32,
dot11RSNAStatsSTAAddress MacAddress,
dot11RSNAStatsVersion Unsigned32,
dot11RSNAStatsSelectedPairwiseCipher OCTET STRING,
dot11RSNAStatsTKIPICVErrors Counter32,
dot11RSNAStatsTKIPLocalMICFailures Counter32,
dot11RSNAStatsTKIPRemoteMICFailures Counter32,
dot11RSNAStatsCCMPReplays Counter32,
dot11RSNAStatsCCMPDecryptErrors Counter32,
dot11RSNAStatsTKIPReplays Counter32,
dot11RSNAStatsCMACICVErrors Counter32,
dot11RSNAStatsCMACReplays Counter32,
dot11RSNAStatsRobustMgmtCCMPReplays Counter32,
dot11RSNABIPMICErrors Counter32 }
dot11RSNAStatsIndex OBJECT-TYPE
SYNTAX Unsigned32 (1..4294967295)
MAX-ACCESS not-accessible
STATUS current
DESCRIPTION
"An auxiliary index into the dot11RSNAStatsTable."
::= { dot11RSNAStatsEntry 1 }
dot11RSNAStatsSTAAddress OBJECT-TYPE
SYNTAX MacAddress
MAX-ACCESS read-only
STATUS current
DESCRIPTION
"This is a status variable.
It is written by the RSNA Key Management in the SME.
The MAC address of the STA to which the statistics in this conceptual row
belong."
::= { dot11RSNAStatsEntry 2 }
dot11RSNAStatsVersion OBJECT-TYPE
SYNTAX Unsigned32 (1..4294967295)
MAX-ACCESS read-only
STATUS current
DESCRIPTION
"This is a status variable.
It is written by the RSNA Key Management in the SME.
The RSNA version with which the STA associated."
::= { dot11RSNAStatsEntry 3 }
dot11RSNAStatsSelectedPairwiseCipher OBJECT-TYPE
SYNTAX OCTET STRING (SIZE(4))
MAX-ACCESS read-only
STATUS current
DESCRIPTION
"This is a status variable.
It is written by the RSNA Key Management in the SME.
The pairwise cipher suite Selector (as defined in 8.4.2.27.2) used during
association, in transmission order."
::= { dot11RSNAStatsEntry 4 }
dot11RSNAStatsTKIPICVErrors OBJECT-TYPE
SYNTAX Counter32
MAX-ACCESS read-only
STATUS current
DESCRIPTION
"This is a status variable.
It is written by the MAC when the condition described below occurs.
Counts the number of TKIP ICV errors encountered when decrypting packets
for the STA."
::= { dot11RSNAStatsEntry 5 }
dot11RSNAStatsTKIPLocalMICFailures OBJECT-TYPE
SYNTAX Counter32
MAX-ACCESS read-only
STATUS current
DESCRIPTION
"This is a status variable.
It is written by the MAC when the condition described below occurs.
Counts the number of MIC failures encountered when checking the integrity
of packets received from the STA at this entity."
::= { dot11RSNAStatsEntry 6 }
dot11RSNAStatsTKIPRemoteMICFailures OBJECT-TYPE
SYNTAX Counter32
MAX-ACCESS read-only
STATUS current
DESCRIPTION
"This is a status variable.
It is written by the MAC when the condition described below occurs.
Counts the number of MIC failures encountered by the STA identified by
dot11StatsSTAAddress and reported back to this entity."
::= { dot11RSNAStatsEntry 7 }
dot11RSNAStatsCCMPReplays OBJECT-TYPE
SYNTAX Counter32
MAX-ACCESS read-only
STATUS current
DESCRIPTION
"This is a status variable.
It is written by the MAC when the condition described below occurs.
The number of received CCMP MPDUs discarded by the replay mechanism."
::= { dot11RSNAStatsEntry 8 }
dot11RSNAStatsCCMPDecryptErrors OBJECT-TYPE
SYNTAX Counter32
MAX-ACCESS read-only
STATUS current
DESCRIPTION
"This is a status variable.
It is written by the MAC when the condition described below occurs.
The number of received MPDUs discarded by the CCMP decryption algorithm."
::= { dot11RSNAStatsEntry 9 }
dot11RSNAStatsTKIPReplays OBJECT-TYPE
SYNTAX Counter32
MAX-ACCESS read-only
STATUS current
DESCRIPTION
"This is a status variable.
It is written by the MAC when the condition described below occurs.
Counts the number of TKIP replay errors detected."
::= { dot11RSNAStatsEntry 10 }
dot11RSNAStatsCMACICVErrors OBJECT-TYPE
SYNTAX Counter32
MAX-ACCESS read-only
STATUS current
DESCRIPTION
"This is a status variable.
It is written by the MAC when the condition described below occurs.
The number of received MPDUs discarded by the CMAC integrity check algorithm."
::= { dot11RSNAStatsEntry 11 }
dot11RSNAStatsCMACReplays OBJECT-TYPE
SYNTAX Counter32
MAX-ACCESS read-only
STATUS current
DESCRIPTION
"This is a status variable.
It is written by the MAC when the condition described below occurs.
The number of received MPDUs discarded by the CMAC replay errors."
::= { dot11RSNAStatsEntry 12 }
dot11RSNAStatsRobustMgmtCCMPReplays OBJECT-TYPE
SYNTAX Counter32
MAX-ACCESS read-only
STATUS current
DESCRIPTION
"This is a status variable.
It is written by the MAC when the condition described below occurs.
The number of received robust management frame MPDUs discarded due to CCMP
replay errors"
::= {dot11RSNAStatsEntry 13}
dot11RSNABIPMICErrors OBJECT-TYPE
SYNTAX Counter32
MAX-ACCESS read-only
STATUS current
DESCRIPTION
"This is a status variable.
It is written by the MAC when the condition described below occurs.
The number of received MMPDUs discarded due to BIP MIC errors"
::= {dot11RSNAStatsEntry 14}
-- ********************************************************************
-- * End of dot11RSNAStats TABLE
-- ********************************************************************
-- **********************************************************************
-- * dot11OperatingClasses TABLE
-- **********************************************************************
dot11OperatingClassesTable OBJECT-TYPE
SYNTAX SEQUENCE OF Dot11OperatingClassesEntry
MAX-ACCESS not-accessible
STATUS current
DESCRIPTION
"(Conceptual) table of attributes for operating classes"
::= {dot11smt 13}
dot11OperatingClassesEntry OBJECT-TYPE
SYNTAX Dot11OperatingClassesEntry
MAX-ACCESS not-accessible
STATUS current
DESCRIPTION
"An entry (conceptual row) in the Operating Classes Table.
IfIndex - Each 802.11 interface is represented by an ifEntry. Interface
tables in this MIB are indexed by ifIndex."
INDEX {ifIndex, dot11OperatingClassesIndex}
::= { dot11OperatingClassesTable 1 }
Dot11OperatingClassesEntry ::=
SEQUENCE {
dot11OperatingClassesIndex Unsigned32,
dot11OperatingClass Unsigned32,
dot11CoverageClass Unsigned32 }
dot11OperatingClassesIndex OBJECT-TYPE
SYNTAX Unsigned32
MAX-ACCESS not-accessible
STATUS current
DESCRIPTION
"The auxiliary variable used to identify instances of the columnar objects
in the Operating Classes Table."
::= { dot11OperatingClassesEntry 1 }
dot11OperatingClass OBJECT-TYPE
SYNTAX Unsigned32
MAX-ACCESS read-write
STATUS current
DESCRIPTION
"This is a control variable.
It is written by the SME or external management entity when the device is
initialized.
This attribute indicates the operating class to be used."
DEFVAL { 0 }
::= { dot11OperatingClassesEntry 2 }
dot11CoverageClass OBJECT-TYPE
SYNTAX Unsigned32
MAX-ACCESS read-write
STATUS current
DESCRIPTION
"This is a control variable.
It is written by the SME or external management entity when the device is
initialized.
This attribute indicates the coverage class to be used."
DEFVAL { 0 }
::= { dot11OperatingClassesEntry 3 }
-- ********************************************************************
-- * End of dot11OperatingClasses TABLE
-- ********************************************************************
-- **********************************************************************
-- * IEEE 802.11 RM and WNM Interface MIB
-- **********************************************************************
-- * The primary interface to the Radio Measurements and Wireless
-- * Network Management functions is meant to be real-time information
-- * obtained through the request/response mechanisms of RM and WNM.
-- * A secondary interface to the measurements and management functions
-- * is through retention of information in this MIB. Non-SNMP requests
-- * for information are obtained via object IDs (OIDs) through the NDIS
-- * or wireless interfaces in the operating systems. SNMP requests for
-- * information are obtained via SNMP SETs and GETs (see [B24]).
-- * dot11RMRequest and dot11RMReport Usage
-- *
-- * The dot11RMRequest and dot11RMReport portions of the RM MIB
-- * provide access to the Radio Measurement service. By performing
-- * SET operations on the various dot11RMRequest MIB objects,
-- * radio measurements may be initiated directly on the local STA or
-- * on any peer station within the same BSS. Subsequently, by
-- * performing GET operations on the various dot11RMReport MIB
-- * objects the results of the requested measurements may be
-- * retrieved.
-- *
-- * In the diagram below, a radio measurement could be initiated
-- * for STA x by performing a MIB.set operation on the RM MIB of
-- * STA x and specifying the MAC address of STA x in
-- * dot11RMRqstTargetAdd. Additionally, it is possible to have STA x
-- * request a measurement from STA y by performing a MIB.set operation
-- * on the SME MIB of STA x and specifying the MAC address of STA y in
-- * dot11RMRqstTargetAdd. In both cases the result of the measurements
-- * can be retrieved by performing a MIB.get operation on the RM MIB
-- * of STA x upon completion of the measurement.
-- *
-- *
-- * MIB.Set MIB.Set
-- * or or
-- * MIB.Get MIB.Get
-- * +========|=========+ +========|=========+
-- * | SME | | | SME | |
-- * | \ / | | \ / |
-- * | +=========+ | | +=========+ |
-- * | | RM and | | | | RM and | |
-- * | | WNM MIB | | | | WNM MIB | |
-- * | | | | | | | |
-- * | | | | | | | |
-- * | +=========+ | | +=========+ |
-- * | | | |
-- * | / \ | | / \ |
-- * | | MREQUEST | | | MREQUEST |
-- * +====+=============+ +====+=============+
-- * | | MREPORT | | | MREPORT |
-- * | \ / MEASURE | Action frames | \ / MEASURE |
-- * | | <==Measurement Request==> | |
-- * | | <==Measurement Report===> | |
-- * | MLME | | MLME |
-- * +==================+ +==================+
-- * STA x STA y
-- *
-- * Each STA maintains a single dot11RMRequestTable in the SME MIB
-- * used to initiate RM Measurement Requests. Each dot11RMRequestEntry
-- * in the table represents an individual Measurement Request that
-- * makes up a complete Measurement Request frame.
-- * Multiple Measurement Requests may be concatenated into a single
-- * Measurement Request frame by setting the same
-- * dot11RMRqstToken value into multiple dot11RMRequestEntrys.
-- *
-- * Each row, dot11RMRequestEntry, of the dot11RMRequestTable
-- * provides read-create access for the initiation of a measurement
-- * request. The dot11RMRequestNextIndex object can be used to
-- * determine which is the next available row. Each row corresponding to
-- * one measurement in the sequence is created with a dot11RMRqstRowStatus
-- * equal to notInService. Once the dot11RMRequestEntry(s) have been
-- * created for a desired measurement sequence the corresponding
-- * dot11RMRqstRowStatus(s) objects are set to active to indicate that
-- * the SME can trigger the appropriate MLME primitives. Upon processing
-- * the request, the SME returns the corresponding dot11RMRqstRowStatus(s)
-- * object to notInService and are now available for additional
-- * measurement requests.
-- *
-- * After a radio measurement is complete the RM populates the RMReport
-- * objects with the results of the measurement. Each STA maintains a set
-- * of RMReport tables, one corresponding to each measurement type. The
-- * results of the entire measurement sequence are spread across the tables
-- * based on the type of measurements requested. Each xxxReportEntry
-- * within a xxxReportTable contains a xxxRprtRqstToken that corresponds
-- * to the original dot11RMRqstToken in the measurement request. So the
-- * results of the measurement can be collected by searching the appropriate
-- * xxxReportTables and retrieve any reports with the matching request
-- * token.
-- *
-- * Similar structures and mechanisms are used for WNM
-- * Request and Reports. The WNM MIB definitions follow the RM MIB definitions
-- * in this Annex.
-- **********************************************************************
-- ********************************************************************
-- * Radio Measurement Interface MIB
-- ********************************************************************
dot11RadioMeasurement OBJECT IDENTIFIER ::= { dot11smt 14 }
-- ********************************************************************
-- * Radio Measurement Requests
-- ********************************************************************
dot11RMRequest OBJECT IDENTIFIER ::= { dot11RadioMeasurement 1 }
-- ********************************************************************
-- * dot11RMRequest TABLE
-- ********************************************************************
dot11RMRequestNextIndex OBJECT-TYPE
SYNTAX Unsigned32(0..65535)
MAX-ACCESS read-only
STATUS current
DESCRIPTION
"This is a status variable.
It is written by the SME when able to accept a new request.
Identifies a hint for the next value of dot11RMRqstIndex to be used in a
row creation attempt for dot11RMRequestTable. If no new rows can be created
for some reason, such as memory, processing requirements, etc., the
SME sets this attribute to 0. It updates this attribute to a proper value
other than 0 as soon as it is capable of receiving new measurement
requests. The nextIndex is not necessarily sequential nor monotonically
increasing."
::= { dot11RMRequest 1 }
dot11RMRequestTable OBJECT-TYPE
SYNTAX SEQUENCE OF Dot11RMRequestEntry
MAX-ACCESS not-accessible
STATUS current
DESCRIPTION
"This group contains the current list of requests for RM reports to be
issued and have been issued until removed. A network manager adds a RM
request by creating a row with createAndWait row status and then filling
in the request parameters/attributes. The request becomes active to be
issued when the row status is set to Active. The columnar objects or
attributes other than the rowStatus are not written if the rowStatus is
Active. The request rows can be deleted, if commanded by a network manager
via changing the value of dot11RMRqstRowStatus to Destroy. This may leave
orphaned rows if a manager crashes and forgets which rows are being used
by it. One recommended way to manage orphaned or finished rows is to
delete rows if their dot11RMRqstRowStatus remains other than Active for
longer than a period (recommend at least 5 minutes, IETF RFC 2579). Or
another recommended way is to delete older rows as needed based on their
dot11RMRqstTimeStamp values. This can be done by the agent as well as the
manager. "
::= { dot11RMRequest 2 }
dot11RMRequestEntry OBJECT-TYPE
SYNTAX Dot11RMRequestEntry
MAX-ACCESS not-accessible
STATUS current
DESCRIPTION
"An entry in the dot11RMRequestTable Indexed by dot11RMRqstIndex."
INDEX { dot11RMRqstIndex }
::= { dot11RMRequestTable 1 }
Dot11RMRequestEntry ::=
SEQUENCE {
dot11RMRqstIndex Unsigned32,
dot11RMRqstRowStatus RowStatus,
dot11RMRqstToken OCTET STRING,
dot11RMRqstRepetitions Unsigned32,
dot11RMRqstIfIndex InterfaceIndex,
dot11RMRqstType INTEGER,
dot11RMRqstTargetAdd MacAddress,
dot11RMRqstTimeStamp TimeTicks,
dot11RMRqstChanNumber Unsigned32,
dot11RMRqstOperatingClass Unsigned32,
dot11RMRqstRndInterval Unsigned32,
dot11RMRqstDuration Unsigned32,
dot11RMRqstParallel TruthValue,
dot11RMRqstEnable TruthValue,
dot11RMRqstRequest TruthValue,
dot11RMRqstReport TruthValue,
dot11RMRqstDurationMandatory TruthValue,
dot11RMRqstBeaconRqstMode INTEGER,
dot11RMRqstBeaconRqstDetail INTEGER,
dot11RMRqstFrameRqstType INTEGER,
dot11RMRqstBssid MacAddress,
dot11RMRqstSSID OCTET STRING,
dot11RMRqstBeaconReportingCondition INTEGER,
dot11RMRqstBeaconThresholdOffset Integer32,
dot11RMRqstSTAStatRqstGroupID INTEGER,
dot11RMRqstLCIRqstSubject INTEGER,
dot11RMRqstLCILatitudeResolution Unsigned32,
dot11RMRqstLCILongitudeResolution Unsigned32,
dot11RMRqstLCIAltitudeResolution Unsigned32,
dot11RMRqstLCIAzimuthType INTEGER,
dot11RMRqstLCIAzimuthResolution Unsigned32,
dot11RMRqstPauseTime Unsigned32,
dot11RMRqstTransmitStreamPeerQSTAAddress MacAddress,
dot11RMRqstTransmitStreamTrafficIdentifier Unsigned32,
dot11RMRqstTransmitStreamBin0Range Unsigned32,
dot11RMRqstTrigdQoSAverageCondition TruthValue,
dot11RMRqstTrigdQoSConsecutiveCondition TruthValue,
dot11RMRqstTrigdQoSDelayCondition TruthValue,
dot11RMRqstTrigdQoSAverageThreshold Unsigned32,
dot11RMRqstTrigdQoSConsecutiveThreshold Unsigned32,
dot11RMRqstTrigdQoSDelayThresholdRange Unsigned32,
dot11RMRqstTrigdQoSDelayThreshold Unsigned32,
dot11RMRqstTrigdQoSMeasurementCount Unsigned32,
dot11RMRqstTrigdQoSTimeout Unsigned32,
dot11RMRqstChannelLoadReportingCondition INTEGER,
dot11RMRqstChannelLoadReference Unsigned32,
dot11RMRqstNoiseHistogramReportingCondition INTEGER,
dot11RMRqstAnpiReference Unsigned32,
dot11RMRqstAPChannelReport OCTET STRING,
dot11RMRqstSTAStatPeerSTAAddress MacAddress,
dot11RMRqstFrameTransmitterAddress MacAddress,
dot11RMRqstVendorSpecific OCTET STRING,
dot11RMRqstSTAStatTrigMeasCount Unsigned32,
dot11RMRqstSTAStatTrigTimeout Unsigned32,
dot11RMRqstSTAStatTrigCondition OCTET STRING,
dot11RMRqstSTAStatTrigSTAFailedCntThresh Unsigned32,
dot11RMRqstSTAStatTrigSTAFCSErrCntThresh Unsigned32,
dot11RMRqstSTAStatTrigSTAMultRetryCntThresh Unsigned32,
dot11RMRqstSTAStatTrigSTAFrameDupeCntThresh Unsigned32,
dot11RMRqstSTAStatTrigSTARTSFailCntThresh Unsigned32,
dot11RMRqstSTAStatTrigSTAAckFailCntThresh Unsigned32,
dot11RMRqstSTAStatTrigSTARetryCntThresh Unsigned32,
dot11RMRqstSTAStatTrigQoSTrigCondition OCTET STRING,
dot11RMRqstSTAStatTrigQoSFailedCntThresh Unsigned32,
dot11RMRqstSTAStatTrigQoSRetryCntThresh Unsigned32,
dot11RMRqstSTAStatTrigQoSMultRetryCntThresh Unsigned32,
dot11RMRqstSTAStatTrigQoSFrameDupeCntThresh Unsigned32,
dot11RMRqstSTAStatTrigQoSRTSFailCntThresh Unsigned32,
dot11RMRqstSTAStatTrigQoSAckFailCntThresh Unsigned32,
dot11RMRqstSTAStatTrigQoSDiscardCntThresh Unsigned32,
dot11RMRqstSTAStatTrigRsnaTrigCondition OCTET STRING,
dot11RMRqstSTAStatTrigRsnaCMACICVErrCntThresh Unsigned32,
dot11RMRqstSTAStatTrigRsnaCMACReplayCntThresh Unsigned32,
dot11RMRqstSTAStatTrigRsnaRobustCCMPReplayCntThresh
Unsigned32,
dot11RMRqstSTAStatTrigRsnaTKIPICVErrCntThresh Unsigned32,
dot11RMRqstSTAStatTrigRsnaTKIPReplayCntThresh Unsigned32,
dot11RMRqstSTAStatTrigRsnaCCMPDecryptErrCntThresh Unsigned32,
dot11RMRqstSTAStatTrigRsnaCCMPReplayCntThresh Unsigned32
}
dot11RMRqstIndex OBJECT-TYPE
SYNTAX Unsigned32
MAX-ACCESS not-accessible
STATUS current
DESCRIPTION
"Index for RM Request elements in dot11RMRequestTable, greater than 0."
::= { dot11RMRequestEntry 1 }
dot11RMRqstRowStatus OBJECT-TYPE
SYNTAX RowStatus
MAX-ACCESS read-create
STATUS current
DESCRIPTION
"This is a control variable.
It is written by an external management entity when requesting a
measurement and by the SME when accepting a measurement request.
The Row Status column of the current row, used for tracking status of an
individual request. When this attribute is set to Active, AND a measurement
request can be unambiguously created based on the parameters in the
row, then the MLME may proceed to issue the request to its intended targets
when appropriate. If not, this attribute may be set to Not-ready
immediately to indicate parametric errors. However, it is the network managers
responsibility to correct the error. If the request is successfully issued
to the target STA, then the rowStatus is set to notInService."
REFERENCE "8.4.2.23"
::= { dot11RMRequestEntry 2 }
dot11RMRqstToken OBJECT-TYPE
SYNTAX OCTET STRING
MAX-ACCESS read-create
STATUS current
DESCRIPTION
"This is a control variable.
It is written by an external management entity when the table entry is
created, i.e., when requesting a measurement..
Changes take effect when dot11RMRqstRowStatus is set to Active.
This attribute indicates a unique string to identify a group of rows to be
issued as parallel or sequential measurements. To guarantee the uniqueness
of this token across multiple network managers, it is recommended that
this token be prefixed with the IP address of the network manager creating
this row. This token is not necessarily equivalent to the measurement
tokens in RM request frames. If this attribute is an empty string, then
this row of request is independent from other requests."
DEFVAL { "" }
::= { dot11RMRequestEntry 3 }
dot11RMRqstRepetitions OBJECT-TYPE
SYNTAX Unsigned32
MAX-ACCESS read-create
STATUS current
DESCRIPTION
"This is a control variable.
It is written by an external management entity when requesting a measurement.
Changes take effect when dot11RMRqstRowStatus is set to Active.
This attribute indicates the requested number of repetitions for all the
measurement request elements in this frame. A value of 0 in the Number of
Repetitions field indicates measurement request elements are executed once
without repetition."
::= { dot11RMRequestEntry 4 }
dot11RMRqstIfIndex OBJECT-TYPE
SYNTAX InterfaceIndex
MAX-ACCESS read-create
STATUS current
DESCRIPTION
"This is a control variable.
It is written by an external management entity when requesting a measurement.
Changes take effect when dot11RMRqstRowStatus is set to Active.
The ifIndex on which this row of the RM Request is to be issued."
::= { dot11RMRequestEntry 5 }
dot11RMRqstType OBJECT-TYPE
SYNTAX INTEGER {
channelLoad(3),
noiseHistogram(4),
beacon(5),
frame(6),
staStatistics(7),
lci(8),
transmitStream(9),
pause(255) }
MAX-ACCESS read-create
STATUS current
DESCRIPTION
"This is a control variable.
It is written by an external management entity when requesting a measurement.
Changes take effect when dot11RMRqstRowStatus is set to Active.
This attribute indicates the measurement type of this RM request row."
::= { dot11RMRequestEntry 6 }
dot11RMRqstTargetAdd OBJECT-TYPE
SYNTAX MacAddress
MAX-ACCESS read-create
STATUS current
DESCRIPTION
"This is a control variable.
It is written by an external management entity when requesting a measurement.
Changes take effect when dot11RMRqstRowStatus is set to Active.
The MAC address of STA for this row of RM Request is to be issued to. If
this attribute matches the MAC address of the dot11RMRqstIfIndex, then
measurement request is for this STA itself to carry out."
::= { dot11RMRequestEntry 7 }
dot11RMRqstTimeStamp OBJECT-TYPE
SYNTAX TimeTicks
MAX-ACCESS read-create
STATUS current
DESCRIPTION
"This is a control variable.
It is written by the SME when dot11RMRequestRowStatus is set to Active.
This attribute indicates the sysUpTime Value the last time when the
dot11RMRqstRowStatus is set to active or when this row is created the
first time."
::= { dot11RMRequestEntry 8 }
dot11RMRqstChanNumber OBJECT-TYPE
SYNTAX Unsigned32
MAX-ACCESS read-create
STATUS current
DESCRIPTION
"This is a control variable.
It is written by an external management entity when requesting a measurement.
Changes take effect when dot11RMRqstRowStatus is set to Active.
The target STA channel number on which to perform the measurements indicated
in this request. The Channel Number is only defined within the indicated
Operating Class for this measurement request. This attribute is
ignored if dot11RMRqstType = STA Statistics Request, LCI Request, Transmit
Stream/Category Measurement, or measurement pause. However, even in that
case, the manager should set this attribute to the current channel for
this interface, so that the row can be set to active when ready with all
attributes indicated."
::= { dot11RMRequestEntry 9 }
dot11RMRqstOperatingClass OBJECT-TYPE
SYNTAX Unsigned32 (1..255)
MAX-ACCESS read-create
STATUS current
DESCRIPTION
"This is a control variable.
It is written by an external management entity when requesting a measurement.
Changes take effect when dot11RMRqstRowStatus is set to Active.
This attribute indicates the channel set for this measurement request.
Country, Operating Class and Channel Number together specify the channel
frequency and spacing for this measurement request. Valid values of Operating
Class are shown in Annex E."
REFERENCE "Annex E"
::= { dot11RMRequestEntry 10 }
dot11RMRqstRndInterval OBJECT-TYPE
SYNTAX Unsigned32
UNITS "TUs"
MAX-ACCESS read-create
STATUS current
DESCRIPTION
"This is a control variable.
It is written by an external management entity when requesting a measurement.
Changes take effect when dot11RMRqstRowStatus is set to Active.
This attribute indicates the upper bound of the random delay to be used
prior to making the measurement, expressed in units of TUs. See 10.11.3.
This attribute is ignored if dot11RMRqstType = STA Statistics Request, LCI
Request, Transmit Stream/Category Measurement or measurement pause."
DEFVAL { 0 }
::= { dot11RMRequestEntry 11 }
dot11RMRqstDuration OBJECT-TYPE
SYNTAX Unsigned32
UNITS "TUs"
MAX-ACCESS read-create
STATUS current
DESCRIPTION
"This is a control variable.
It is written by an external management entity when requesting a measurement.
Changes take effect when dot11RMRqstRowStatus is set to Active.
This attribute indicates the preferred or mandatory measurement duration
for this Measurement Request. This attribute is ignored if dot11RMRqstType
= LCI Request or measurement pause."
DEFVAL { 0 }
::= { dot11RMRequestEntry 12 }
dot11RMRqstParallel OBJECT-TYPE
SYNTAX TruthValue
MAX-ACCESS read-create
STATUS current
DESCRIPTION
"This is a control variable.
It is written by an external management entity when requesting a measurement.
Changes take effect when dot11RMRqstRowStatus is set to Active.
This attribute indicates the parallel bit for this Measurement Request
element. This attribute, when false, indicates that the measurement is
performed in sequence. This attribute, when true, indicates that this measurement
should start at the same time as the measurement described by the
next Measurement Request element in the next row if the next row indicates
the same value for dot11RMRqstToken."
DEFVAL { false }
::= { dot11RMRequestEntry 13 }
dot11RMRqstEnable OBJECT-TYPE
SYNTAX TruthValue
MAX-ACCESS read-create
STATUS current
DESCRIPTION
"This is a control variable.
It is written by an external management entity when requesting a measurement.
Changes take effect when dot11RMRqstRowStatus is set to Active.
This attribute indicates the enable bit for this Measurement Request element."
DEFVAL { false }
::= { dot11RMRequestEntry 14 }
dot11RMRqstRequest OBJECT-TYPE
SYNTAX TruthValue
MAX-ACCESS read-create
STATUS current
DESCRIPTION
"This is a control variable.
It is written by an external management entity when requesting a measurement.
Changes take effect when dot11RMRqstRowStatus is set to Active.
This attribute indicates the request bit for this Measurement Request element.
This attribute, when true, indicates that this STA accepts measurement
requests from the target STA."
DEFVAL { false }
::= { dot11RMRequestEntry 15 }
dot11RMRqstReport OBJECT-TYPE
SYNTAX TruthValue
MAX-ACCESS read-create
STATUS current
DESCRIPTION
"This is a control variable.
It is written by an external management entity when requesting a measurement.
Changes take effect when dot11RMRqstRowStatus is set to Active.
This attribute indicates the report bit for this Measurement Request element.
This attribute, when true, indicates that the target STA may enable
autonomous measurement reports to the requesting STA."
DEFVAL { false }
::= { dot11RMRequestEntry 16 }
dot11RMRqstDurationMandatory OBJECT-TYPE
SYNTAX TruthValue
MAX-ACCESS read-create
STATUS current
DESCRIPTION
"This is a control variable.
It is written by an external management entity when requesting a measurement.
Changes take effect when dot11RMRqstRowStatus is set to Active.
This attribute indicates the duration mandatory bit for this Measurement
Request element. This attribute, when true, indicates that the indicated
Measurement Duration is a mandatory duration for this measurement. This
attribute, when false, indicates that the indicated Measurement Duration
is a maximum duration for this measurement."
DEFVAL { false }
::= { dot11RMRequestEntry 17 }
dot11RMRqstBeaconRqstMode OBJECT-TYPE
SYNTAX INTEGER {
passive(0),
active(1),
beaconTable(2) }
MAX-ACCESS read-create
STATUS current
DESCRIPTION
"This is a control variable.
It is written by an external management entity when requesting a measurement.
Changes take effect when dot11RMRqstRowStatus is set to Active.
This attribute indicates the Measurement Mode for this Beacon Request element.
This attribute is only valid if the dot11RMRqstType is 5, indicating
a beacon request, and is ignored otherwise."
DEFVAL { 0 }
::= { dot11RMRequestEntry 18 }
dot11RMRqstBeaconRqstDetail OBJECT-TYPE
SYNTAX INTEGER {
noBody(0),
fixedFieldsAndRequestedElements(1),
allBody(2) }
MAX-ACCESS read-create
STATUS current
DESCRIPTION
"This is a control variable.
It is written by an external management entity when requesting a measurement.
Changes take effect when dot11RMRqstRowStatus is set to Active.
dot11RMRqstBeaconRqstDetail indicates the Reporting Detail for Beacon
Request element. This attribute is only valid if the dot11RMRqstType is 5,
indicating a beacon request, and is ignored otherwise."
DEFVAL { 2 }
::= { dot11RMRequestEntry 19 }
dot11RMRqstFrameRqstType OBJECT-TYPE
SYNTAX INTEGER { frameCountRep(1) }
MAX-ACCESS read-create
STATUS current
DESCRIPTION
"This is a control variable.
It is written by an external management entity when requesting a measurement.
Changes take effect when dot11RMRqstRowStatus is set to Active.
dot11RMRqstFrameRqstType indicates the Frame Request Type for Frame
Request element. This attribute is only valid if the dot11RMRqstType is 6,
indicating a frame request, and is ignored otherwise."
DEFVAL { 1 }
::= { dot11RMRequestEntry 20 }
dot11RMRqstBssid OBJECT-TYPE
SYNTAX MacAddress
MAX-ACCESS read-create
STATUS current
DESCRIPTION
"This is a control variable.
It is written by an external management entity when requesting a measurement.
Changes take effect when dot11RMRqstRowStatus is set to Active.
BSSID indicates the BSSID of the particular AP for which this measurement
is requested. The BSSID is set to the wildcard BSSID when the measurement
is to be performed on any AP(s) on the indicated channel. This attribute
is only valid if the dot11RMRqstType is 5, indicating a beacon request,
and is ignored otherwise."
DEFVAL { 'FFFFFFFFFFFF'H }
::= { dot11RMRequestEntry 21 }
dot11RMRqstSSID OBJECT-TYPE
SYNTAX OCTET STRING (SIZE(0..32))
MAX-ACCESS read-create
STATUS current
DESCRIPTION
"This is a control variable.
It is written by an external management entity when requesting a measurement.
Changes take effect when dot11RMRqstRowStatus is set to Active.
This attribute indicates the SSID for the measurement. Zero length MIB
element for SSID indicates the wildcard SSID. The SSID is set to the wildcard
SSID when the measurement is to be performed on all ESSs/IBSSs on the
indicated channel. This attribute is only valid if the dot11RMRqstType is
5, indicating a beacon request, and is ignored otherwise."
DEFVAL { ''H }
::= { dot11RMRequestEntry 22 }
dot11RMRqstBeaconReportingCondition OBJECT-TYPE
SYNTAX INTEGER {
afterEveryMeasurement(0),
rcpiAboveAbsoluteThreshold(1),
rcpiBelowAbsoluteThreshold(2),
rsniAboveAbsoluteThreshold(3),
rsniBelowAbsoluteThreshold(4),
rcpiAboveOffsetThreshold(5),
rcpiBelowOffsetThreshold(6),
rsniAboveOffsetThreshold(7),
rsniBelowOffsetThreshold(8),
rcpiInBound(9),
rsniInBound(10) }
MAX-ACCESS read-create
STATUS current
DESCRIPTION
"This is a control variable.
It is written by an external management entity when requesting a measurement.
Changes take effect when dot11RMRqstRowStatus is set to Active.
This attribute indicates when the Beacon Measurement results are to be
reported to the requesting STA. This attribute is only valid if the
dot11RMRqstType is 5, indicating a beacon request, and is ignored otherwise."
REFERENCE
"IEEE 802.11, Table 8-66-Reporting Condition values for Beacon Request element"
DEFVAL {0}
::= { dot11RMRequestEntry 23 }
dot11RMRqstBeaconThresholdOffset OBJECT-TYPE
SYNTAX Integer32
MAX-ACCESS read-create
STATUS current
DESCRIPTION
"This is a control variable.
It is written by an external management entity when requesting a measurement.
Changes take effect when dot11RMRqstRowStatus is set to Active.
Threshold/Offset provides either the threshold value or the offset value
to be used for conditional reporting. For indicated Reporting Conditions
1-4, the integer range is (0..255). For indicated Reporting Conditions 5-
10, the integer range is (-127..+127). This attribute is only valid if
the dot11RMRqstType is 5, indicating a beacon request, and is ignored otherwise."
DEFVAL { 0 }
::= { dot11RMRequestEntry 24 }
dot11RMRqstSTAStatRqstGroupID OBJECT-TYPE
SYNTAX INTEGER {
dot11CountersTable(0),
dot11MacStatistics(1),
dot11QosCountersTableforUP0(2),
dot11QosCountersTableforUP1(3),
dot11QosCountersTableforUP2(4),
dot11QosCountersTableforUP3(5),
dot11QosCountersTableforUP4(6),
dot11QosCountersTableforUP5(7),
dot11QosCountersTableforUP6(8),
dot11QosCountersTableforUP7(9),
bSSAverageAccessDelays(10),
dot11CountersGroup3Tablefor31(11),
dot11CountersGroup3Tablefor32(12),
dot11CountersGroup3Tablefor33(13),
dot11CountersGroup3Tablefor34(14),
dot11CountersGroup3Tablefor35(15),
dot11RSNAStatsTable(16)}
MAX-ACCESS read-create
STATUS current
DESCRIPTION
"This is a control variable.
It is written by an external management entity when requesting a measurement.
Changes take effect when dot11RMRqstRowStatus is set to Active.
The attribute indicates the group identity for this Measurement Request
element. This attribute is only valid if the dot11RMRqstType is 7, indicating
a statistics request, and is ignored otherwise."
DEFVAL { 0 }
::= { dot11RMRequestEntry 25 }
dot11RMRqstLCIRqstSubject OBJECT-TYPE
SYNTAX INTEGER { local(0), remote(1) }
MAX-ACCESS read-create
STATUS current
DESCRIPTION
"This is a control variable.
It is written by an external management entity when requesting a measurement.
Changes take effect when dot11RMRqstRowStatus is set to Active.
The attribute indicates the subject of the LCI measurement request. This
attribute is only valid if the dot11RMRqstType is 8, indicating an LCI
request, and is ignored otherwise."
DEFVAL { 0 }
::= { dot11RMRequestEntry 26 }
dot11RMRqstLCILatitudeResolution OBJECT-TYPE
SYNTAX Unsigned32 (0..63)
MAX-ACCESS read-create
STATUS current
DESCRIPTION
"This is a control variable.
It is written by an external management entity when requesting a measurement.
Changes take effect when dot11RMRqstRowStatus is set to Active.
This attribute is 6 bits indicating the number of valid
bits in the fixed-point value of Latitude of the LCI measurement request.
This attribute is only valid if the dot11RMRqstType is 8, indicating an
LCI request, and is ignored otherwise."
::= { dot11RMRequestEntry 27 }
dot11RMRqstLCILongitudeResolution OBJECT-TYPE
SYNTAX Unsigned32 (0..63)
MAX-ACCESS read-create
STATUS current
DESCRIPTION
"This is a control variable.
It is written by an external management entity when requesting a measurement.
Changes take effect when dot11RMRqstRowStatus is set to Active.
This attribute is 6 bits indicating the number of valid bits in the fixedpoint
value of Longitude of the LCI measurement request. This attribute is
only valid if the dot11RMRqstType is 8, indicating an LCI request, and is
ignored otherwise."
::= { dot11RMRequestEntry 28 }
dot11RMRqstLCIAltitudeResolution OBJECT-TYPE
SYNTAX Unsigned32 (0..63)
MAX-ACCESS read-create
STATUS current
DESCRIPTION
"This is a control variable.
It is written by an external management entity when requesting a measurement.
Changes take effect when dot11RMRqstRowStatus is set to Active.
This attribute is 6 bits indicating the number of valid
bits in the fixed-point value of Altitude of the LCI measurement
request. This attribute is only valid if the dot11RMRqstType is 8, indicating
an LCI request, and is ignored otherwise."
::= { dot11RMRequestEntry 29 }
dot11RMRqstLCIAzimuthType OBJECT-TYPE
SYNTAX INTEGER { frontSurfaceofSta(0), radioBeam(1) }
MAX-ACCESS read-create
STATUS current
DESCRIPTION
"This is a control variable.
It is written by an external management entity when requesting a measurement.
Changes take effect when dot11RMRqstRowStatus is set to Active.
This attribute indicates the azimuth reference for the LCI Azimuth measurement
request. This attribute is only valid if the dot11RMRqstType is
8, indicating an LCI request, and is ignored otherwise."
DEFVAL{ 0 }
::= { dot11RMRequestEntry 30 }
dot11RMRqstLCIAzimuthResolution OBJECT-TYPE
SYNTAX Unsigned32 (0..15)
MAX-ACCESS read-create
STATUS current
DESCRIPTION
"This is a control variable.
It is written by an external management entity when requesting a measurement.
Changes take effect when dot11RMRqstRowStatus is set to Active.
This attribute is 4 bits indicating the number of valid
bits in the fixed-point value of Azimuth of the LCI Azimuth
measurement request. This attribute is only valid if the dot11RMRqstType
is 8, indicating an LCI request, and is ignored otherwise."
::= { dot11RMRequestEntry 31 }
dot11RMRqstPauseTime OBJECT-TYPE
SYNTAX Unsigned32 (0..65535)
UNITS "10 TUs"
MAX-ACCESS read-create
STATUS current
DESCRIPTION
"This is a control variable.
It is written by an external management entity when requesting a measurement.
Changes take effect when dot11RMRqstRowStatus is set to Active.
This attribute is a 16 bit unsigned integer number
representing the time period for which measurements are
suspended or paused. Measurement pause requests are used to
provide time delays between the execution times of measurement
request elements in a Measurement Request frame. This attribute is only
valid if the dot11RMRqstType is 255, indicating an pause request, and is
ignored otherwise."
DEFVAL { 0 }
::= { dot11RMRequestEntry 32 }
dot11RMRqstTransmitStreamPeerQSTAAddress OBJECT-TYPE
SYNTAX MacAddress
MAX-ACCESS read-create
STATUS current
DESCRIPTION
"This is a control variable.
It is written by an external management entity when requesting a measurement.
Changes take effect when dot11RMRqstRowStatus is set to Active.
This attribute indicates the peer STA address to be measured for a Transmit
Stream/Category Measurement measurement. This attribute is only valid
if the dot11RMRqstType is 9, indicating a transmit stream/category
request, and is ignored otherwise."
::= { dot11RMRequestEntry 33 }
dot11RMRqstTransmitStreamTrafficIdentifier OBJECT-TYPE
SYNTAX Unsigned32(0..16)
MAX-ACCESS read-create
STATUS current
DESCRIPTION
"This is a control variable.
It is written by an external management entity when requesting a measurement.
Changes take effect when dot11RMRqstRowStatus is set to Active.
This attribute indicates the TC, or TS to be measured for a Transmit
Stream/Category Measurement measurement. This attribute is only valid if
the dot11RMRqstType is 9, indicating a transmit stream/category request,
and is ignored otherwise."
::= { dot11RMRequestEntry 34 }
dot11RMRqstTransmitStreamBin0Range OBJECT-TYPE
SYNTAX Unsigned32(1..255)
MAX-ACCESS read-create
STATUS current
DESCRIPTION
"This is a control variable.
It is written by an external management entity when requesting a measurement.
Changes take effect when dot11RMRqstRowStatus is set to Active.
This attribute indicates the delay range for bin 0 of the transmit delay
histogram. This attribute is only valid if the dot11RMRqstType is 9, indicating
a transmit stream/category request, and is ignored otherwise."
::= { dot11RMRequestEntry 35 }
dot11RMRqstTrigdQoSAverageCondition OBJECT-TYPE
SYNTAX TruthValue
MAX-ACCESS read-create
STATUS current
DESCRIPTION
"This is a control variable.
It is written by an external management entity when requesting a measurement.
Changes take effect when dot11RMRqstRowStatus is set to Active.
This attribute, when true, indicates a request for triggered reporting
with trigger based on the number of discarded MSDUs reaching the
dot11RMRqstTrigdQoSAverageThreshold when averaged over
dot11RMRqstTrigdQoSMEasurementCount consecutive MSDUs. This attribute is
only valid if the dot11RMRqstType is 9, indicating a transmit stream/category
request, and is ignored otherwise."
DEFVAL { false }
::= { dot11RMRequestEntry 36 }
dot11RMRqstTrigdQoSConsecutiveCondition OBJECT-TYPE
SYNTAX TruthValue
MAX-ACCESS read-create
STATUS current
DESCRIPTION
"This is a control variable.
It is written by an external management entity when requesting a measurement.
Changes take effect when dot11RMRqstRowStatus is set to Active.
This attribute, when true, indicates a request for triggered reporting
with trigger based on the consecutive number of MSDUs discarded reaching
dot11RMRqstTrigdQoSConsecutiveThreshold. This attribute is only valid if
the dot11RMRqstType is 9, indicating a transmit stream/category request,
and is ignored otherwise."
DEFVAL { false }
::= { dot11RMRequestEntry 37 }
dot11RMRqstTrigdQoSDelayCondition OBJECT-TYPE
SYNTAX TruthValue
MAX-ACCESS read-create
STATUS current
DESCRIPTION
"This is a control variable.
It is written by an external management entity when requesting a measurement.
Changes take effect when dot11RMRqstRowStatus is set to Active.
This attribute, when true, indicates a request for triggered reporting
with trigger based on the consecutive number of MSDUs that experience a
transmit delay greater than dot11RMRqstTrigdQoSDelayThresholdRange reaching
dot11RMRqstTrigdQoSDelayThreshold. This attribute is only valid if the
dot11RMRqstType is 9, indicating a transmit stream/category request, and
is ignored otherwise."
DEFVAL { false }
::= { dot11RMRequestEntry 38 }
dot11RMRqstTrigdQoSAverageThreshold OBJECT-TYPE
SYNTAX Unsigned32 (1..255)
MAX-ACCESS read-create
STATUS current
DESCRIPTION
"This is a control variable.
It is written by an external management entity when requesting a measurement.
Changes take effect when dot11RMRqstRowStatus is set to Active.
This attribute indicates the trigger threshold for triggered Transmit
Stream/Category Measurement based on average MSDUs discarded. Trigger
occurs if the number of MSDUs discarded over the moving average number of
transmitted MSDUs in dot11RMRqstTrigdQoSMeasurementCount reaches this
threshold. This attribute is only valid if the dot11RMRqstType is 9, indicating
a transmit stream/category request, and is ignored otherwise."
DEFVAL { 10 }
::= { dot11RMRequestEntry 39 }
dot11RMRqstTrigdQoSConsecutiveThreshold OBJECT-TYPE
SYNTAX Unsigned32 (1..255)
MAX-ACCESS read-create
STATUS current
DESCRIPTION
"This is a control variable.
It is written by an external management entity when requesting a measurement.
Changes take effect when dot11RMRqstRowStatus is set to Active.
This attribute indicates the trigger threshold for triggered Transmit
Stream/Category Measurement based on consecutive MSDUs discarded. Trigger
occurs if the consecutive number of MSDUs discarded reaches this threshold.
This attribute is only valid if the dot11RMRqstType is 9, indicating
a transmit stream/category request, and is ignored otherwise."
DEFVAL { 5 }
::= { dot11RMRequestEntry 40 }
dot11RMRqstTrigdQoSDelayThresholdRange OBJECT-TYPE
SYNTAX Unsigned32 (0..3)
MAX-ACCESS read-create
STATUS current
DESCRIPTION
"This is a control variable.
It is written by an external management entity when requesting a measurement.
Changes take effect when dot11RMRqstRowStatus is set to Active.
This attribute indicates the minimum transmit delay for delayed MSDU
counts. Trigger occurs if the a consecutive number of MSDUs experience a
transmit delay greater than or equal to the lower bound of the bin of the
Transmit Delay Histogram given by the value of this attribute + 2, e.g. if
this attribute is 1 the lower bound of bin 3. This attribute is only valid
if the dot11RMRqstType is 9, indicating a transmit stream/category
request, and is ignored otherwise."
DEFVAL { 1 }
::= { dot11RMRequestEntry 41 }
dot11RMRqstTrigdQoSDelayThreshold OBJECT-TYPE
SYNTAX Unsigned32 (1..255)
MAX-ACCESS read-create
STATUS current
DESCRIPTION
"This is a control variable.
It is written by an external management entity when requesting a measurement.
Changes take effect when dot11RMRqstRowStatus is set to Active.
This attribute indicates the number of consecutive delayed MSDUs needed
for trigger. Trigger occurs if the consecutive number of MSDUs that experience
a transmit delay greater than dot11RMRqstQoSDelayThresholdRange
reaches this value. This attribute is only valid if the dot11RMRqstType is
9, indicating a transmit stream/category request, and is ignored otherwise."
DEFVAL { 20 }
::= { dot11RMRequestEntry 42 }
dot11RMRqstTrigdQoSMeasurementCount OBJECT-TYPE
SYNTAX Unsigned32 (1..255)
MAX-ACCESS read-create
STATUS current
DESCRIPTION
"This is a control variable.
It is written by an external management entity when requesting a measurement.
Changes take effect when dot11RMRqstRowStatus is set to Active.
This attribute indicates the number of MSDUs to be used as a moving average
count in the average error threshold and in determining the scope of
the reported Transmit Stream/Category measurement in a triggered measurement
report. This attribute is only valid if the dot11RMRqstType is 9,
indicating a transmit stream/category request, and is ignored otherwise."
DEFVAL { 100 }
::= { dot11RMRequestEntry 43 }
dot11RMRqstTrigdQoSTimeout OBJECT-TYPE
SYNTAX Unsigned32 (1..255)
UNITS "100 TUs"
MAX-ACCESS read-create
STATUS current
DESCRIPTION
"This is a control variable.
It is written by an external management entity when requesting a measurement.
Changes take effect when dot11RMRqstRowStatus is set to Active.
This attribute indicates the timeout interval during which a measuring STA
does not generate further triggered Transmit Stream/Category measurement
reports after a trigger condition has been met and a report generated.
This attribute is only valid if the dot11RMRqstType is 9, indicating a
transmit stream/category request, and is ignored otherwise."
DEFVAL { 20 }
::= { dot11RMRequestEntry 44 }
dot11RMRqstChannelLoadReportingCondition OBJECT-TYPE
SYNTAX INTEGER {
afterEveryMeasurement(0),
chanLoadAboveReference(1),
chanLoadBelowReference(2) }
MAX-ACCESS read-create
STATUS current
DESCRIPTION
"This is a control variable.
It is written by an external management entity when requesting a measurement.
Changes take effect when dot11RMRqstRowStatus is set to Active.
This attribute indicates when the Channel Load Measurement results are to
be reported to the requesting STA. This attribute is only valid if the
dot11RMRqstType is 3, indicating a channel load request, and is ignored
otherwise."
REFERENCE
"IEEE 802.11, Table 8-61-Reporting Condition values for Channel Load
Request element"
DEFVAL {0}
::= { dot11RMRequestEntry 45 }
dot11RMRqstChannelLoadReference OBJECT-TYPE
SYNTAX Unsigned32 (0..255)
UNITS "1/255"
MAX-ACCESS read-create
STATUS current
DESCRIPTION
"This is a control variable.
It is written by an external management entity when requesting a measurement.
Changes take effect when dot11RMRqstRowStatus is set to Active.
This attribute indicates the channel load reporting condition reference
value. The measured Channel Load is compared to this reference value and a
report is issued if the reporting condition is satisfied. The reference
value is in the same units as Channel Load and represents the fractional
time of the measurement duration during which the STA determined the channel
to be busy. This attribute is only valid if the dot11RMRqstType is 3,
indicating a channel load request, and is ignored otherwise."
DEFVAL { 5 }
::= { dot11RMRequestEntry 46 }
dot11RMRqstNoiseHistogramReportingCondition OBJECT-TYPE
SYNTAX INTEGER {
afterEveryMeasurement(0),
aNPIAboveReference(1),
aNPIBelowReference(2) }
MAX-ACCESS read-create
STATUS current
DESCRIPTION
"This is a control variable.
It is written by an external management entity when requesting a measurement.
Changes take effect when dot11RMRqstRowStatus is set to Active.
This attribute indicates when the Noise Histogram Measurement results are
to be reported to the requesting STA. This attribute is only valid if the
dot11RMRqstType is 4, indicating a noise histogram request, and is ignored
otherwise."
REFERENCE
"IEEE 802.11, Table 8-63-Reporting Condition for Noise Histogram Report"
DEFVAL {0}
::= { dot11RMRequestEntry 47 }
dot11RMRqstAnpiReference OBJECT-TYPE
SYNTAX Unsigned32 (0..255)
MAX-ACCESS read-create
STATUS current
DESCRIPTION
"This is a control variable.
It is written by an external management entity when requesting a measurement.
Changes take effect when dot11RMRqstRowStatus is set to Active.
This attribute indicates the noise histogram reporting condition ANPI reference
value. The measured ANPI is compared to this reference value and a
report is issued if the indicated reporting condition is satisfied.
ANPIval = Int[(ANPIpower in dBm + 110)*2], for ANPI in the range -110 dBm
to 0 dBm. ANPIval = 220 for ANPI > 0 dBm. ANPIval = 255 when ANPI is not
available. This attribute is only valid if the dot11RMRqstType is 4, indicating
a noise histogram request, and is ignored otherwise."
DEFVAL { 5 }
::= { dot11RMRequestEntry 48 }
dot11RMRqstAPChannelReport OBJECT-TYPE
SYNTAX OCTET STRING (SIZE(0..255))
MAX-ACCESS read-create
STATUS current
DESCRIPTION
"This is a control variable.
It is written by an external management entity when requesting a measurement.
Changes take effect when dot11RMRqstRowStatus is set to Active.
This attribute indicates the specific channels to be used for the
requested beacon measurements. The default value is null. Each octet indicates
a different channel within the indicated Operating Class. This list
of channels is the Channel List in the AP Channel Report element described
in 8.4.2.38. This attribute is only valid if the dot11RMRqstType is 5,
indicating a beacon request, and is ignored otherwise."
DEFVAL { ''H }
::= { dot11RMRequestEntry 49 }
dot11RMRqstSTAStatPeerSTAAddress OBJECT-TYPE
SYNTAX MacAddress
MAX-ACCESS read-create
STATUS current
DESCRIPTION
"This is a control variable.
It is written by an external management entity when requesting a measurement.
Changes take effect when dot11RMRqstRowStatus is set to Active.
This attribute indicates the peer STA address to be measured for a statistics
request. This attribute is only valid if the dot11RMRqstType is 7,
indicating a statistics request, and is ignored otherwise."
::= { dot11RMRequestEntry 50 }
dot11RMRqstFrameTransmitterAddress OBJECT-TYPE
SYNTAX MacAddress
MAX-ACCESS read-create
STATUS current
DESCRIPTION
"This is a control variable.
It is written by an external management entity when requesting a measurement.
Changes take effect when dot11RMRqstRowStatus is set to Active.
This attribute indicates the Transmitter Address (TA) of the frames to be
counted in this frame request. This attribute is only valid if the
dot11RMRqstType is 6, indicating a frame request, and is ignored otherwise."
::= { dot11RMRequestEntry 51 }
dot11RMRqstVendorSpecific OBJECT-TYPE
SYNTAX OCTET STRING (SIZE(0..255))
MAX-ACCESS read-create
STATUS current
DESCRIPTION
"This is a control variable.
It is written by an external management entity when requesting a measurement.
Changes take effect when dot11RMRqstRowStatus is set to Active.
This attribute provides an envelope for any optional vendor specific subelements
which may be included in a measurement request element. The
default value is null. This attribute is valid for all requests."
DEFVAL { ''H }
::= { dot11RMRequestEntry 52 }
dot11RMRqstSTAStatTrigMeasCount OBJECT-TYPE
SYNTAX Unsigned32
MAX-ACCESS read-create
STATUS current
DESCRIPTION
"This attribute indicates the number of MSDUs or MPDUs over which the
trigger criterion is applied. This attribute is only valid if
dot11RMRqstType is 7 (STA Statistics) and if the value of the attribute is
not equal to 0."
DEFVAL { 0 }
::= { dot11RMRequestEntry 53 }
dot11RMRqstSTAStatTrigTimeout OBJECT-TYPE
SYNTAX Unsigned32(0..65535)
UNITS "100 TUs"
MAX-ACCESS read-create
STATUS current
DESCRIPTION
"This attribute indicates the interval during which a measuring STA does
not generate further triggered STA Statistics Reports after a trigger condition
has been met. This attribute is only valid if dot11RMRqstType is 7
(STA Statistics)."
DEFVAL { 0 }
::= { dot11RMRequestEntry 54 }
dot11RMRqstSTAStatTrigCondition OBJECT-TYPE
SYNTAX OCTET STRING (SIZE(2))
MAX-ACCESS read-create
STATUS current
DESCRIPTION
"This attribute indicates the trigger values used when requesting triggered
STA Statistics
reporting. The format of the STA Counter Trigger Condition field is shown
in Figure 8-118."
::= { dot11RMRequestEntry 55 }
dot11RMRqstSTAStatTrigSTAFailedCntThresh OBJECT-TYPE
SYNTAX Unsigned32
MAX-ACCESS read-create
STATUS current
DESCRIPTION
"This attribute indicates that a STA Statistics Report should be generated
(triggered) when the dot11FailedCount value has increased more than the
threshold value indicated here. The counter increase is measured over the
last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 56 }
dot11RMRqstSTAStatTrigSTAFCSErrCntThresh OBJECT-TYPE
SYNTAX Unsigned32
MAX-ACCESS read-create
STATUS current
DESCRIPTION
"This attribute indicates that a STA Statistics Report should be generated
(triggered) when the dot11FCSErrorCount value has increased more than the
threshold value indicated here. The counter increase is measured over the
last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 57 }
dot11RMRqstSTAStatTrigSTAMultRetryCntThresh OBJECT-TYPE
SYNTAX Unsigned32
MAX-ACCESS read-create
STATUS current
DESCRIPTION
"This attribute indicates that a STA Statistics Report should be generated
(triggered) when the dot11MultipleRetryCount value has increased more than
the threshold value indicated here. The counter increase is measured over
the last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 58 }
dot11RMRqstSTAStatTrigSTAFrameDupeCntThresh OBJECT-TYPE
SYNTAX Unsigned32
MAX-ACCESS read-create
STATUS current
DESCRIPTION
"This attribute indicates that a STA Statistics Report should be generated
(triggered) when the dot11FrameDuplicateCount value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 59 }
dot11RMRqstSTAStatTrigSTARTSFailCntThresh OBJECT-TYPE
SYNTAX Unsigned32
MAX-ACCESS read-create
STATUS current
DESCRIPTION
"This attribute indicates that a STA Statistics Report should be generated
(triggered) when the dot11RTSFailureCount value has increased more than
the threshold value indicated here. The counter increase is measured over
the last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 60 }
dot11RMRqstSTAStatTrigSTAAckFailCntThresh OBJECT-TYPE
SYNTAX Unsigned32
MAX-ACCESS read-create
STATUS current
DESCRIPTION
"This attribute indicates that a STA Statistics Report should be generated
(triggered) when the dot11ACKFailureCount value has increased more than
the threshold value indicated here. The counter increase is measured over
the last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 61 }
dot11RMRqstSTAStatTrigSTARetryCntThresh OBJECT-TYPE
SYNTAX Unsigned32
MAX-ACCESS read-create
STATUS current
DESCRIPTION
"This attribute indicates that a STA Statistics Report should be generated
(triggered) when the dot11RetryCount value has increased more than the
threshold value indicated here. The counter increase is measured over the
last n MSDUs or MPDUs, where n is the value of
dot11RMRqstSTAStatTrigMeasCount. This attribute is only valid if
dot11RMRqstType is 7 (STA Statistics), and if
dot11RMRqstSTAStatRqstGroupID is 0 (dot11CountersTable) and if the value
of the attribute is not equal to 0."
DEFVAL { 0 }
::= { dot11RMRequestEntry 62 }
dot11RMRqstSTAStatTrigQoSTrigCondition OBJECT-TYPE
SYNTAX OCTET STRING (SIZE(2))
MAX-ACCESS read-create
STATUS current
DESCRIPTION
"This attribute indicates the trigger values used when requesting triggered
QoS STA Statistics
reporting. The format of the STA Counter Trigger Condition field is shown
in Figure 8-120."
::= { dot11RMRequestEntry 63 }
dot11RMRqstSTAStatTrigQoSFailedCntThresh OBJECT-TYPE
SYNTAX Unsigned32
MAX-ACCESS read-create
STATUS current
DESCRIPTION
"This attribute indicates that a STA Statistics Report should be generated
(triggered) when the dot11QosFailedCount value has increased more than the
threshold value indicated here. The counter increase is measured over the
last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 64 }
dot11RMRqstSTAStatTrigQoSRetryCntThresh OBJECT-TYPE
SYNTAX Unsigned32
MAX-ACCESS read-create
STATUS current
DESCRIPTION
"This attribute indicates that a STA Statistics Report should be generated
(triggered) when the dot11QosRetryCount value has increased more than the
threshold value indicated here. The counter increase is measured over the
last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 65 }
dot11RMRqstSTAStatTrigQoSMultRetryCntThresh OBJECT-TYPE
SYNTAX Unsigned32
MAX-ACCESS read-create
STATUS current
DESCRIPTION
"This attribute indicates that a STA Statistics Report should be generated
(triggered) when the dot11QosMultipleRetryCount value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 66 }
dot11RMRqstSTAStatTrigQoSFrameDupeCntThresh OBJECT-TYPE
SYNTAX Unsigned32
MAX-ACCESS read-create
STATUS current
DESCRIPTION
"This attribute indicates that a STA Statistics Report should be generated
(triggered) when the dot11QosFrameDuplicateCount value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 67 }
dot11RMRqstSTAStatTrigQoSRTSFailCntThresh OBJECT-TYPE
SYNTAX Unsigned32
MAX-ACCESS read-create
STATUS current
DESCRIPTION
"This attribute indicates that a STA Statistics Report should be generated
(triggered) when the dot11QosRTSFailureCount value has increased more than
the threshold value indicated here. The counter increase is measured over
the last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 68 }
dot11RMRqstSTAStatTrigQoSAckFailCntThresh OBJECT-TYPE
SYNTAX Unsigned32
MAX-ACCESS read-create
STATUS current
DESCRIPTION
"This attribute indicates that a STA Statistics Report should be generated
(triggered) when the dot11QosACKFailureCount value has increased more than
the threshold value indicated here. The counter increase is measured over
the last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 69 }
dot11RMRqstSTAStatTrigQoSDiscardCntThresh OBJECT-TYPE
SYNTAX Unsigned32
MAX-ACCESS read-create
STATUS current
DESCRIPTION
"This attribute indicates that a STA Statistics Report should be generated
(triggered) when the dot11QosDiscardedFrameCount value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 2 to 9 (dot11QosCountersTable) and if the
value of the attribute is not equal to 0."
DEFVAL { 0 }
::= { dot11RMRequestEntry 70 }
dot11RMRqstSTAStatTrigRsnaTrigCondition OBJECT-TYPE
SYNTAX OCTET STRING (SIZE(2))
MAX-ACCESS read-create
STATUS current
DESCRIPTION
"This attribute indicates the trigger values used when requesting triggered
RSNA STA Statistics
reporting. The format of the STA Counter Trigger Condition field is shown
in Figure 8-122."
::= { dot11RMRequestEntry 71 }
dot11RMRqstSTAStatTrigRsnaCMACICVErrCntThresh OBJECT-TYPE
SYNTAX Unsigned32
MAX-ACCESS read-create
STATUS current
DESCRIPTION
"This attribute indicates that a STA Statistics Report should be generated
(triggered) when the dot11RSNAStatsCMACICVErrors value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 72 }
dot11RMRqstSTAStatTrigRsnaCMACReplayCntThresh OBJECT-TYPE
SYNTAX Unsigned32
MAX-ACCESS read-create
STATUS current
DESCRIPTION
"This attribute indicates that a STA Statistics Report should be generated
(triggered) when the dot11RSNAStatsCMACReplays value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 73 }
dot11RMRqstSTAStatTrigRsnaRobustCCMPReplayCntThresh OBJECT-TYPE
SYNTAX Unsigned32
MAX-ACCESS read-create
STATUS current
DESCRIPTION
"This attribute indicates that a STA Statistics Report should be generated
(triggered) when the dot11RSNAStatsRobustMgmtCCMPReplays value has
increased more than the threshold value indicated here. The counter
increase is measured over the last n MSDUs or MPDUs, where n is the value
of dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 74 }
dot11RMRqstSTAStatTrigRsnaTKIPICVErrCntThresh OBJECT-TYPE
SYNTAX Unsigned32
MAX-ACCESS read-create
STATUS current
DESCRIPTION
"This attribute indicates that a STA Statistics Report should be generated
(triggered) when the dot11RSNAStatsTKIPICVErrors value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 75 }
dot11RMRqstSTAStatTrigRsnaTKIPReplayCntThresh OBJECT-TYPE
SYNTAX Unsigned32
MAX-ACCESS read-create
STATUS current
DESCRIPTION
"This attribute indicates that a STA Statistics Report should be generated
(triggered) when the dot11RSNAStatsTKIPReplays value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 76 }
dot11RMRqstSTAStatTrigRsnaCCMPDecryptErrCntThresh OBJECT-TYPE
SYNTAX Unsigned32
MAX-ACCESS read-create
STATUS current
DESCRIPTION
"This attribute indicates that a STA Statistics Report should be generated
(triggered) when the dot11RSNAStatsCCMPDecryptErrors value has increased
more than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 77 }
dot11RMRqstSTAStatTrigRsnaCCMPReplayCntThresh OBJECT-TYPE
SYNTAX Unsigned32
MAX-ACCESS read-create
STATUS current
DESCRIPTION
"This attribute indicates that a STA Statistics Report should be generated
(triggered) when the dot11RSNAStatsCCMPReplays value has increased more
than the threshold value indicated here. The counter increase is measured
over the last n MSDUs or MPDUs, where n is the value of
dot11RMRqstSTAStatTrigMeasCount. This attribute is only valid if
dot11RMRqstType is 7 (STA Statistics), and if
dot11RMRqstSTAStatRqstGroupID is 16 (dot11RSNAStatsTable) and if the value
of the attribute is not equal to 0."
DEFVAL { 0 }
::= { dot11RMRequestEntry 78 }
-- **********************************************************************
-- * End of dot11RMRequest TABLE
-- **********************************************************************
-- ********************************************************************
-- * Radio Measurement Reports
-- * Report tables contain measurement reports received by this STA or
-- * results of measurements performed by this STA.
-- ********************************************************************
dot11RMReport OBJECT IDENTIFIER ::= { dot11RadioMeasurement 2 }
-- ********************************************************************
-- * dot11ChannelLoadReport TABLE
-- ********************************************************************
dot11ChannelLoadReportTable OBJECT-TYPE
SYNTAX SEQUENCE OF Dot11ChannelLoadReportEntry
MAX-ACCESS not-accessible
STATUS current
DESCRIPTION
"This table contains the current list of Channel Load reports that have been
received by the MLME. The report tables are maintained as a FIFO to preserve
freshness, thus the rows in this table can be deleted for memory
constraints or other implementation constraints determined by the vendor.
New rows have different RprtIndex values than those deleted within the
range limitation of the index. One easy way is to monotonically increase
RprtIndex for new reports being written in the table."
::= { dot11RMReport 1 }
dot11ChannelLoadReportEntry OBJECT-TYPE
SYNTAX Dot11ChannelLoadReportEntry
MAX-ACCESS not-accessible
STATUS current
DESCRIPTION
"An entry in the dot11ChannelLoadReportTable Indexed by
dot11ChannelLoadRprtIndex."
INDEX { dot11ChannelLoadRprtIndex }
::= { dot11ChannelLoadReportTable 1 }
Dot11ChannelLoadReportEntry ::=
SEQUENCE {
dot11ChannelLoadRprtIndex Unsigned32,
dot11ChannelLoadRprtRqstToken OCTET STRING,
dot11ChannelLoadRprtIfIndex InterfaceIndex,
dot11ChannelLoadMeasuringSTAAddr MacAddress,
dot11ChannelLoadRprtChanNumber Unsigned32,
dot11ChannelLoadRprtOperatingClass Unsigned32,
dot11ChannelLoadRprtActualStartTime TSFType,
dot11ChannelLoadRprtMeasurementDuration Unsigned32,
dot11ChannelLoadRprtChannelLoad Unsigned32,
dot11ChannelLoadRprtVendorSpecific OCTET STRING,
dot11ChannelLoadRprtMeasurementMode INTEGER }
dot11ChannelLoadRprtIndex OBJECT-TYPE
SYNTAX Unsigned32
MAX-ACCESS not-accessible
STATUS current
DESCRIPTION
"Index for Channel Load Report elements in dot11ChannelLoadReportTable,
greater than 0."
::= { dot11ChannelLoadReportEntry 1 }
dot11ChannelLoadRprtRqstToken OBJECT-TYPE
SYNTAX OCTET STRING
MAX-ACCESS read-only
STATUS current
DESCRIPTION
"This is a status variable.
It is written by the SME when a measurement report is completed.
This attribute indicates the request token that was indicated in the Measurement
request that generated this measurement report. This should be an
exact match to the original dot11RMRqstToken attribute. Note that there
may be multiple entries in the table that match this value since a single
request may generate multiple measurement reports."
::= { dot11ChannelLoadReportEntry 2 }
dot11ChannelLoadRprtIfIndex OBJECT-TYPE
SYNTAX InterfaceIndex
MAX-ACCESS read-only
STATUS current
DESCRIPTION
"This is a status variable.
It is written by the SME when a measurement report is completed.
The ifIndex of the interface over which this ChannelLoad Report was
received."
::= { dot11ChannelLoadReportEntry 3 }
dot11ChannelLoadMeasuringSTAAddr OBJECT-TYPE
SYNTAX MacAddress
MAX-ACCESS read-only
STATUS current
DESCRIPTION
"This is a status variable.
It is written by the SME when a measurement report is completed.
The MAC address of the measuring STA for this row of the Channel Load
report."
::= { dot11ChannelLoadReportEntry 4 }
dot11ChannelLoadRprtChanNumber OBJECT-TYPE
SYNTAX Unsigned32
MAX-ACCESS read-only
STATUS current
DESCRIPTION
"This is a status variable.
It is written by the SME when a measurement report is completed.
This attribute indicates the channel number used for this Channel Load
Report. The Channel Number is only defined within the indicated Operating
Class for this measurement report."
::= { dot11ChannelLoadReportEntry 5 }
dot11ChannelLoadRprtOperatingClass OBJECT-TYPE
SYNTAX Unsigned32(1..255)
MAX-ACCESS read-only
STATUS current
DESCRIPTION
"This is a status variable.
It is written by the SME when a measurement report is completed.
This attribute indicates the channel set for this measurement report.
Country, Operating Class and Channel Number together specify the channel
frequency and spacing for this measurement report. Valid values of Operating
Class are shown in Annex E."
REFERENCE "Annex E"
::= { dot11ChannelLoadReportEntry 6 }
dot11ChannelLoadRprtActualStartTime OBJECT-TYPE
SYNTAX TSFType
MAX-ACCESS read-only
STATUS current
DESCRIPTION
"This is a status variable.
It is written by the SME when a measurement report is completed.
This attribute indicates the TSF value at the time when the
measurement started."
::= { dot11ChannelLoadReportEntry 7 }
dot11ChannelLoadRprtMeasurementDuration OBJECT-TYPE
SYNTAX Unsigned32
UNITS "TUs"
MAX-ACCESS read-only
STATUS current
DESCRIPTION
"This is a status variable.
It is written by the SME when a measurement report is completed.
This attribute indicates the duration over which the ChannelLoad Report
was measured."
::= { dot11ChannelLoadReportEntry 8 }
dot11ChannelLoadRprtChannelLoad OBJECT-TYPE
SYNTAX Unsigned32(0..255)
UNITS "1/255"
MAX-ACCESS read-only
STATUS current
DESCRIPTION
"This is a status variable.
It is written by the SME when a measurement report is completed.
Channel Load contains the fractional duration over which the measuring STA
determined the channel to be busy during the measurement duration."
REFERENCE "8.4.2.24.5"
::= { dot11ChannelLoadReportEntry 9 }
dot11ChannelLoadRprtVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11ChannelLoadReportEntry 10 }
dot11ChannelLoadRprtMeasurementMode OBJECT-TYPE
SYNTAX INTEGER {
success(0),
incapableBit(1),
refusedBit(2)
}
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11ChannelLoadReportEntry 11 }
-- ********************************************************************
-- * End of dot11ChannelLoadReport TABLE
-- ********************************************************************
-- ********************************************************************
-- * dot11NoiseHistogramReport TABLE
-- ********************************************************************
dot11NoiseHistogramReportTable OBJECT-TYPE
SYNTAX SEQUENCE OF Dot11NoiseHistogramReportEntry
MAX-ACCESS not-accessible
STATUS current
DESCRIPTION
"This table contains the current list of Noise Histogram reports that have
been received by the MLME. The report tables are maintained as a FIFO to
preserve freshness, thus the rows in this table can be deleted for memory
constraints or other implementation constraints determined by the vendor.
New rows have different RprtIndex values than those deleted within the
range limitation of the index. One easy way is to monotonically increase
RprtIndex for new reports being written in the table."
::= { dot11RMReport 2 }
dot11NoiseHistogramReportEntry OBJECT-TYPE
SYNTAX Dot11NoiseHistogramReportEntry
MAX-ACCESS not-accessible
STATUS current
DESCRIPTION
"An entry in the dot11NoiseHistogramReportTable Indexed by
dot11NoiseHistogramRprtIndex."
INDEX { dot11NoiseHistogramRprtIndex }
::= { dot11NoiseHistogramReportTable 1 }
Dot11NoiseHistogramReportEntry ::=
SEQUENCE {
dot11NoiseHistogramRprtIndex Unsigned32,
dot11NoiseHistogramRprtRqstToken OCTET STRING,
dot11NoiseHistogramRprtIfIndex InterfaceIndex,
dot11NoiseHistogramMeasuringSTAAddr MacAddress,
dot11NoiseHistogramRprtChanNumber Unsigned32,
dot11NoiseHistogramRprtOperatingClass Unsigned32,
dot11NoiseHistogramRprtActualStartTime TSFType,
dot11NoiseHistogramRprtMeasurementDuration Unsigned32,
dot11NoiseHistogramRprtAntennaID Unsigned32,
dot11NoiseHistogramRprtANPI Unsigned32,
dot11NoiseHistogramRprtIPIDensity0 Unsigned32,
dot11NoiseHistogramRprtIPIDensity1 Unsigned32,
dot11NoiseHistogramRprtIPIDensity2 Unsigned32,
dot11NoiseHistogramRprtIPIDensity3 Unsigned32,
dot11NoiseHistogramRprtIPIDensity4 Unsigned32,
dot11NoiseHistogramRprtIPIDensity5 Unsigned32,
dot11NoiseHistogramRprtIPIDensity6 Unsigned32,
dot11NoiseHistogramRprtIPIDensity7 Unsigned32,
dot11NoiseHistogramRprtIPIDensity8 Unsigned32,
dot11NoiseHistogramRprtIPIDensity9 Unsigned32,
dot11NoiseHistogramRprtIPIDensity10 Unsigned32,
dot11NoiseHistogramRprtVendorSpecific OCTET STRING,
dot11NoiseHistogramRprtMeasurementMode INTEGER}
dot11NoiseHistogramRprtIndex OBJECT-TYPE
SYNTAX Unsigned32
MAX-ACCESS not-accessible
STATUS current
DESCRIPTION
"Index for Noise Histogram elements in dot11NoiseHistogramReportTable,
greater than 0."
::= { dot11NoiseHistogramReportEntry 1 }
dot11NoiseHistogramRprtRqstToken OBJECT-TYPE
SYNTAX OCTET STRING
MAX-ACCESS read-only
STATUS current
DESCRIPTION
"This is a status variable.
It is written by the SME when a measurement report is completed.
This attribute indicates the request token that was indicated in the measurement
request that generated this measurement report. This should be an
exact match to the original dot11RMRqstToken attribute. Note that there
may be multiple entries in the table that match this value since a single
request may generate multiple measurement reports."
::= { dot11NoiseHistogramReportEntry 2 }
dot11NoiseHistogramRprtIfIndex OBJECT-TYPE
SYNTAX InterfaceIndex
MAX-ACCESS read-only
STATUS current
DESCRIPTION
"This is a status variable.
It is written by the SME when a measurement report is completed.
The ifIndex of the interface over which this Noise Histogram Report was
received. "
::= { dot11NoiseHistogramReportEntry 3 }
dot11NoiseHistogramMeasuringSTAAddr OBJECT-TYPE
SYNTAX MacAddress
MAX-ACCESS read-only
STATUS current
DESCRIPTION
"This is a status variable.
It is written by the SME when a measurement report is completed.
The MAC address of the measuring STA for this row of Noise Histogram
report."
::= { dot11NoiseHistogramReportEntry 4 }
dot11NoiseHistogramRprtChanNumber OBJECT-TYPE
SYNTAX Unsigned32
MAX-ACCESS read-only
STATUS current
DESCRIPTION
"This is a status variable.
It is written by the SME when a measurement report is completed.
This attribute indicates the channel number used for this Noise Histogram
Report. The Channel Number is only defined within the indicated Operating
Class for this measurement report."
::= { dot11NoiseHistogramReportEntry 5 }
dot11NoiseHistogramRprtOperatingClass OBJECT-TYPE
SYNTAX Unsigned32(1..255)
MAX-ACCESS read-only
STATUS current
DESCRIPTION
"This is a status variable.
It is written by the SME when a measurement report is completed.
This attribute indicates the channel set for this measurement report.
Country, Operating Class and Channel Number together specify the channel
frequency and spacing for this measurement report. Valid values of Operating
Class are shown in Annex E."
REFERENCE "Annex E"
::= { dot11NoiseHistogramReportEntry 6 }
dot11NoiseHistogramRprtActualStartTime OBJECT-TYPE
SYNTAX TSFType
MAX-ACCESS read-only
STATUS current
DESCRIPTION
"This is a status variable.
It is written by the SME when a measurement report is completed.
This attribute indicates the TSF value at the time when the
measurement started."
::= { dot11NoiseHistogramReportEntry 7 }
dot11NoiseHistogramRprtMeasurementDuration OBJECT-TYPE
SYNTAX Unsigned32
UNITS "TUs"
MAX-ACCESS read-only
STATUS current
DESCRIPTION
"This is a status variable.
It is written by the SME when a measurement report is completed.
This attribute indicates the duration over which the Noise Histogram
Report was measured."
::= { dot11NoiseHistogramReportEntry 8 }
dot11NoiseHistogramRprtAntennaID OBJECT-TYPE
SYNTAX Unsigned32(0..255)
MAX-ACCESS read-only
STATUS current
DESCRIPTION
"This is a status variable.
It is written by the SME when a measurement report is completed.
This attribute indicates the identifying number for the antenna used for
this measurement. The value 0 indicates that the antenna identifier is
unknown. The value 255 indicates that the measurement was made with multiple
antennas or that the antenna ID is unknown. The value 1 is used for a
STA with only one antenna. STAs with more than one antenna assign Antenna
IDs to each antenna as consecutive, ascending numbers. Each Antenna ID
number represents a unique antenna characterized by a fixed relative position,
a fixed relative direction, and a peak gain for that position and
direction."
::= { dot11NoiseHistogramReportEntry 9 }
dot11NoiseHistogramRprtANPI OBJECT-TYPE
SYNTAX Unsigned32(0..255)
MAX-ACCESS read-only
STATUS current
DESCRIPTION
"This is a status variable.
It is written by the SME when a measurement report is completed.
This attribute indicates the Average Noise Power Indicator (ANPI) for this
Noise Histogram measurement. The ANPI value represents the average noise
plus interference power on the measured channel at the antenna connector
during the measurement duration. To calculate ANPI, the STA measures and
uses IPI in the indicated channel when NAV is equal to 0 (when virtual CS
mechanism indicates idle channel) except during frame transmission or
reception."
::= { dot11NoiseHistogramReportEntry 10 }
dot11NoiseHistogramRprtIPIDensity0 OBJECT-TYPE
SYNTAX Unsigned32
MAX-ACCESS read-only
STATUS current
DESCRIPTION
"This is a status variable.
It is written by the SME when a measurement report is completed.
This attribute indicates the measured IPI density for non-IEEE-802.11 signals
with measured power satisfying the condition: Power <= -92dBm."
::= { dot11NoiseHistogramReportEntry 11 }
dot11NoiseHistogramRprtIPIDensity1 OBJECT-TYPE
SYNTAX Unsigned32
MAX-ACCESS read-only
STATUS current
DESCRIPTION
"This is a status variable.
It is written by the SME when a measurement report is completed.
This attribute indicates the measured IPI density for non-IEEE-802.11 signals
with measured power satisfying the condition: -92dBm < Power <= -
89dBm."
::= { dot11NoiseHistogramReportEntry 12 }
dot11NoiseHistogramRprtIPIDensity2 OBJECT-TYPE
SYNTAX Unsigned32
MAX-ACCESS read-only
STATUS current
DESCRIPTION
"This is a status variable.
It is written by the SME when a measurement report is completed.
This attribute indicates the measured IPI density for non-IEEE-802.11 signals
with measured power satisfying the condition: -89dBm < Power <= -
86dBm."
::= { dot11NoiseHistogramReportEntry 13 }
dot11NoiseHistogramRprtIPIDensity3 OBJECT-TYPE
SYNTAX Unsigned32
MAX-ACCESS read-only
STATUS current
DESCRIPTION
"This is a status variable.
It is written by the SME when a measurement report is completed.
This attribute indicates the measured IPI density for non-IEEE-802.11 signals
with measured power satisfying the condition: -86dBm < Power <= -
83dBm."
::= { dot11NoiseHistogramReportEntry 14 }
dot11NoiseHistogramRprtIPIDensity4 OBJECT-TYPE
SYNTAX Unsigned32
MAX-ACCESS read-only
STATUS current
DESCRIPTION
"This is a status variable.
It is written by the SME when a measurement report is completed.
This attribute indicates the measured IPI density for non-IEEE-802.11 signals
with measured power satisfying the condition: -83dBm < Power <= -
80dBm."
::= { dot11NoiseHistogramReportEntry 15 }
dot11NoiseHistogramRprtIPIDensity5 OBJECT-TYPE
SYNTAX Unsigned32
MAX-ACCESS read-only
STATUS current
DESCRIPTION
"This is a status variable.
It is written by the SME when a measurement report is completed.
This attribute indicates the measured IPI density for non-IEEE-802.11 signals
with measured power satisfying the condition: -80dBm < Power <= -
75dBm."
::= { dot11NoiseHistogramReportEntry 16 }
dot11NoiseHistogramRprtIPIDensity6 OBJECT-TYPE
SYNTAX Unsigned32
MAX-ACCESS read-only
STATUS current
DESCRIPTION
"This is a status variable.
It is written by the SME when a measurement report is completed.
This attribute indicates the measured IPI density for non-IEEE-802.11 signals
with measured power satisfying the condition:
-75dBm < Power <= -70dBm."
::= { dot11NoiseHistogramReportEntry 17 }
dot11NoiseHistogramRprtIPIDensity7 OBJECT-TYPE
SYNTAX Unsigned32
MAX-ACCESS read-only
STATUS current
DESCRIPTION
"This is a status variable.
It is written by the SME when a measurement report is completed.
This attribute indicates the measured IPI density for non-IEEE-802.11 signals
with measured power satisfying the condition:
-70dBm < Power <= -65dBm."
::= { dot11NoiseHistogramReportEntry 18 }
dot11NoiseHistogramRprtIPIDensity8 OBJECT-TYPE
SYNTAX Unsigned32
MAX-ACCESS read-only
STATUS current
DESCRIPTION
"This is a status variable.
It is written by the SME when a measurement report is completed.
This attribute indicates the measured IPI density for non-IEEE-802.11 signals
with measured power satisfying the condition:
-65dBm < Power <= -60dBm."
::= { dot11NoiseHistogramReportEntry 19 }
dot11NoiseHistogramRprtIPIDensity9 OBJECT-TYPE
SYNTAX Unsigned32
MAX-ACCESS read-only
STATUS current
DESCRIPTION
"This is a status variable.
It is written by the SME when a measurement report is completed.
This attribute indicates the measured IPI density for non-IEEE-802.11 signals
with measured power satisfying the condition:
-60dBm < Power <= -55dBm."
::= { dot11NoiseHistogramReportEntry 20 }
dot11NoiseHistogramRprtIPIDensity10 OBJECT-TYPE
SYNTAX Unsigned32
MAX-ACCESS read-only
STATUS current
DESCRIPTION
"This is a status variable.
It is written by the SME when a measurement report is completed.
This attribute indicates the measured IPI density for non-IEEE-802.11 signals
with measured power satisfying the condition:
-55dBm < Power."
::= { dot11NoiseHistogramReportEntry 21 }
dot11NoiseHistogramRprtVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11NoiseHistogramReportEntry 22 }
dot11NoiseHistogramRprtMeasurementMode OBJECT-TYPE
SYNTAX INTEGER {
success(0),
incapableBit(1),
refusedBit(2) }
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11NoiseHistogramReportEntry 23 }
-- ********************************************************************
-- * End of dot11NoiseHistogramReport TABLE
-- ********************************************************************
-- ********************************************************************
-- * dot11BeaconReport TABLE
-- ********************************************************************
dot11BeaconReportTable OBJECT-TYPE
SYNTAX SEQUENCE OF Dot11BeaconReportEntry
MAX-ACCESS not-accessible
STATUS current
DESCRIPTION
"This table contains the current list of Beacon reports that have been
received by the MLME. The report tables are maintained as FIFO to preserve
freshness, thus the rows in this table can be deleted for memory constraints
or other implementation constraints determined by the vendor. New
rows have different RprtIndex values than those deleted within the range
limitation of the index. One easy way is to monotonically increase RprtIndex
for new reports being written in the table."
::= { dot11RMReport 3 }
dot11BeaconReportEntry OBJECT-TYPE
SYNTAX Dot11BeaconReportEntry
MAX-ACCESS not-accessible
STATUS current
DESCRIPTION
"An entry in the dot11BeaconReportTable Indexed by dot11BeaconRprtIndex."
INDEX { dot11BeaconRprtIndex }
::= { dot11BeaconReportTable 1 }
Dot11BeaconReportEntry ::=
SEQUENCE {
dot11BeaconRprtIndex Unsigned32,
dot11BeaconRprtRqstToken OCTET STRING,
dot11BeaconRprtIfIndex InterfaceIndex,
dot11BeaconMeasuringSTAAddr MacAddress,
dot11BeaconRprtChanNumber Unsigned32,
dot11BeaconRprtOperatingClass Unsigned32,
dot11BeaconRprtActualStartTime TSFType,
dot11BeaconRprtMeasurementDuration Unsigned32,
dot11BeaconRprtPhyType INTEGER,
dot11BeaconRprtReportedFrameType INTEGER,
dot11BeaconRprtRCPI Unsigned32,
dot11BeaconRprtRSNI Unsigned32,
dot11BeaconRprtBSSID MacAddress,
dot11BeaconRprtAntennaID Unsigned32,
dot11BeaconRprtParentTSF TSFType,
dot11BeaconRprtReportedFrameBody OCTET STRING,
dot11BeaconRprtVendorSpecific OCTET STRING,
dot11BeaconRprtMeasurementMode INTEGER}
dot11BeaconRprtIndex OBJECT-TYPE
SYNTAX Unsigned32
MAX-ACCESS not-accessible
STATUS current
DESCRIPTION
"Index for Beacon Reports in dot11BeaconReportTable, greater than 0."
::= { dot11BeaconReportEntry 1 }
dot11BeaconRprtRqstToken OBJECT-TYPE
SYNTAX OCTET STRING
MAX-ACCESS read-only
STATUS current
DESCRIPTION
"This is a status variable.
It is written by the SME when a measurement report is completed.
This attribute indicates the request token that was indicated in the measurement
request that generated this measurement report. This should be an
exact match to the original dot11RMRqstToken attribute. Note that there
may be multiple entries in the table that match this value since a single
request may generate multiple measurement reports."
::= { dot11BeaconReportEntry 2 }
dot11BeaconRprtIfIndex OBJECT-TYPE
SYNTAX InterfaceIndex
MAX-ACCESS read-only
STATUS current
DESCRIPTION
"This is a status variable.
It is written by the SME when a measurement report is completed.
The ifIndex of the interface over which this Beacon Report was received."
::= { dot11BeaconReportEntry 3 }
dot11BeaconMeasuringSTAAddr OBJECT-TYPE
SYNTAX MacAddress
MAX-ACCESS read-only
STATUS current
DESCRIPTION
"This is a status variable.
It is written by the SME when a measurement report is completed.
The MAC address of the measuring STA for this row of Beacon report."
::= { dot11BeaconReportEntry 4 }
dot11BeaconRprtChanNumber OBJECT-TYPE
SYNTAX Unsigned32
MAX-ACCESS read-only
STATUS current
DESCRIPTION
"This is a status variable.
It is written by the SME when a measurement report is completed.
This attribute indicates the channel number used for this Beacon Report.
The Channel Number is only defined within the indicated Operating Class
for this measurement report."
::= { dot11BeaconReportEntry 5 }
dot11BeaconRprtOperatingClass OBJECT-TYPE
SYNTAX Unsigned32(1..255)
MAX-ACCESS read-only
STATUS current
DESCRIPTION
"This is a status variable.
It is written by the SME when a measurement report is completed.
This attribute indicates the channel set for this measurement report.
Country, Operating Class and Channel Number together specify the channel
frequency and spacing for this measurement report. Valid values of Operating
Class are shown in Annex E."
REFERENCE "Annex E"
::= { dot11BeaconReportEntry 6 }
dot11BeaconRprtActualStartTime OBJECT-TYPE
SYNTAX TSFType
MAX-ACCESS read-only
STATUS current
DESCRIPTION
"This is a status variable.
It is written by the SME when a measurement report is completed.
This attribute indicates the TSF value at the time when the measurement
started."
::= { dot11BeaconReportEntry 7 }
dot11BeaconRprtMeasurementDuration OBJECT-TYPE
SYNTAX Unsigned32
UNITS "TUs"
MAX-ACCESS read-only
STATUS current
DESCRIPTION
"This is a status variable.
It is written by the SME when a measurement report is completed.
This attribute indicates the duration over which the Beacon Report was
measured."
::= { dot11BeaconReportEntry 8 }
dot11BeaconRprtPhyType OBJECT-TYPE
SYNTAX INTEGER {
fhss(1),
dsss(2),
irbaseband(3),
ofdm(4),
hrdsss(5),
erp(6),
ht(7) }
UNITS "dot11PHYType"
MAX-ACCESS read-only
STATUS current
DESCRIPTION
"This is a status variable.
It is written by the SME when a measurement report is completed.
This attribute indicates the PHY Type for this row of Beacon Report."
::= { dot11BeaconReportEntry 9 }
dot11BeaconRprtReportedFrameType OBJECT-TYPE
SYNTAX INTEGER { beaconOrProbeResponse(0), measurementPilot(1) }
MAX-ACCESS read-only
STATUS current
DESCRIPTION
"This is a status variable.
It is written by the SME when a measurement report is completed.
This attribute indicates the frame type reported in
dot11BeaconRprtReportedFrameBody"
::= { dot11BeaconReportEntry 10 }
dot11BeaconRprtRCPI OBJECT-TYPE
SYNTAX Unsigned32(0..255)
MAX-ACCESS read-only
STATUS current
DESCRIPTION
"This is a status variable.
It is written by the SME when a measurement report is completed.
This attribute indicates the received channel power of the beacon or probe
response frame in dBm, as defined in the RCPI measurement subclause for
the indicated PHY Type.
RCPIval = Int[(RCPIpower in dBm + 110)*2], for RCPI in the range -110 dBm
to 0 dBm. RCPIval = 220 for RCPI > 0 dBm. RCPIval = 255 when RCPI is not
available."
::= { dot11BeaconReportEntry 11 }
dot11BeaconRprtRSNI OBJECT-TYPE
SYNTAX Unsigned32(0..255)
MAX-ACCESS read-only
STATUS current
DESCRIPTION
"This is a status variable.
It is written by the SME when a measurement report is completed.
This attribute indicates the received signal to noise ratio of the beacon
or probe response frame in dB. RSNI is the received signal to noise plus
interference ratio derived from the measured RCPI for the received frame
and from the measured ANPI for the channel used to receive the frame. RSNI
is calculated by the ratio of the received signal power (RCPI - ANPI)
over the noise plus interference power (ANPI) where
RSNI = [(ratio(dB) + 10) * 2], for ratios in the range -10dB to +118dB."
::= { dot11BeaconReportEntry 12 }
dot11BeaconRprtBSSID OBJECT-TYPE
SYNTAX MacAddress
MAX-ACCESS read-only
STATUS current
DESCRIPTION
"This is a status variable.
It is written by the SME when a measurement report is completed.
This attribute indicates the BSSID of the beacon for this row of Beacon
Report."
::= { dot11BeaconReportEntry 13 }
dot11BeaconRprtAntennaID OBJECT-TYPE
SYNTAX Unsigned32(0..255)
MAX-ACCESS read-only
STATUS current
DESCRIPTION
"This is a status variable.
It is written by the SME when a measurement report is completed.
This attribute indicates the identifying number for the antenna used for
this measurement. The value 0 indicates that the antenna identifier is
unknown. The value 255 indicates that this measurement was made with multiple
antennas. The value 1 is used for a STA with only one antenna. STAs
with more than one antenna assign Antenna IDs to each antenna as consecutive,
ascending numbers. Each Antenna ID number represents a unique
antenna characterized by a fixed relative position, a fixed relative
direction, and a peak gain for that position and direction."
::= { dot11BeaconReportEntry 14 }
dot11BeaconRprtParentTSF OBJECT-TYPE
SYNTAX TSFType
MAX-ACCESS read-only
STATUS current
DESCRIPTION
"This is a status variable.
It is written by the SME when a measurement report is completed.
This attribute indicates the TSF value of the serving measuring STA's TSF
value at the time the measuring STA received the beacon or probe response
frame."
::= { dot11BeaconReportEntry 15 }
dot11BeaconRprtReportedFrameBody OBJECT-TYPE
SYNTAX OCTET STRING (SIZE(0..100))
MAX-ACCESS read-only
STATUS current
DESCRIPTION
"This is a status variable.
It is written by the SME when a measurement report is completed.
This attribute indicates the fixed fields and elements from the frame body
of the Beacon, Measurement Pilot or Probe Response frame being received.
All reported TIM elements are truncated to 4 octets."
::= { dot11BeaconReportEntry 16 }
dot11BeaconRprtVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11BeaconReportEntry 17 }
dot11BeaconRprtMeasurementMode OBJECT-TYPE
SYNTAX INTEGER {
success(0),
incapableBit(1),
refusedBit(2) }
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11BeaconReportEntry 18 }
-- ********************************************************************
-- * End of dot11BeaconReport TABLE
-- ********************************************************************
-- ********************************************************************
-- * dot11FrameReport TABLE
-- ********************************************************************
dot11FrameReportTable OBJECT-TYPE
SYNTAX SEQUENCE OF Dot11FrameReportEntry
MAX-ACCESS not-accessible
STATUS current
DESCRIPTION
"This table contains the current list of Frame reports that have been
received by the MLME. The report tables are maintained as a FIFO to preserve
freshness, thus the rows in this table can be deleted for memory
constraints or other implementation constraints determined by the vendor.
New rows have different RprtIndex values than those deleted within the
range limitation of the index. One easy way is to monotonically increase
RprtIndex for new reports being written in the table."
::= { dot11RMReport 4 }
dot11FrameReportEntry OBJECT-TYPE
SYNTAX Dot11FrameReportEntry
MAX-ACCESS not-accessible
STATUS current
DESCRIPTION
"An entry in the dot11FrameReportTable Indexed by dot11FrameRprtIndex."
INDEX { dot11FrameRprtIndex }
::= { dot11FrameReportTable 1 }
Dot11FrameReportEntry ::=
SEQUENCE {
dot11FrameRprtIndex Unsigned32,
dot11FrameRprtIfIndex InterfaceIndex,
dot11FrameRprtRqstToken Unsigned32,
dot11FrameRprtChanNumber Unsigned32,
dot11FrameRprtOperatingClass Unsigned32,
dot11FrameRprtActualStartTime TSFType,
dot11FrameRprtMeasurementDuration Unsigned32,
dot11FrameRprtTransmitSTAAddress MacAddress,
dot11FrameRprtBSSID MacAddress,
dot11FrameRprtPhyType INTEGER,
dot11FrameRprtAvgRCPI Unsigned32,
dot11FrameRprtLastRSNI Unsigned32,
dot11FrameRprtLastRCPI Unsigned32,
dot11FrameRprtAntennaID Unsigned32,
dot11FrameRprtNumberFrames Unsigned32,
dot11FrameRprtVendorSpecific OCTET STRING,
dot11FrameRptMeasurementMode INTEGER}
dot11FrameRprtIndex OBJECT-TYPE
SYNTAX Unsigned32
MAX-ACCESS not-accessible
STATUS current
DESCRIPTION
"Index for Frame Report elements in dot11FrameReportTable, greater than
0."
::= { dot11FrameReportEntry 1 }
dot11FrameRprtIfIndex OBJECT-TYPE
SYNTAX InterfaceIndex
MAX-ACCESS read-only
STATUS current
DESCRIPTION
"This is a status variable.
It is written by the SME when a measurement report is completed.
The ifIndex of the interface over which this Frame Report was received."
::= { dot11FrameReportEntry 2 }
dot11FrameRprtRqstToken OBJECT-TYPE
SYNTAX Unsigned32
MAX-ACCESS read-only
STATUS current
DESCRIPTION
"This is a status variable.
It is written by the SME when a measurement report is completed.
INDEX for Frame Request elements in dot11FrameRequestTable that corresponds
to this row of frame report. Since a single frame request can generate
multiple rows in the frame report table, one per BSSID, this
dot11FrameRprtRqstToken indicates which request this particular row indicates.
If this row of report is received without a particular request,
this attribute should be 0"
::= { dot11FrameReportEntry 3 }
dot11FrameRprtChanNumber OBJECT-TYPE
SYNTAX Unsigned32
MAX-ACCESS read-only
STATUS current
DESCRIPTION
"This is a status variable.
It is written by the SME when a measurement report is completed.
This attribute indicates the channel number used for this Frame Report.
The Channel Number is only defined within the indicated Operating Class
for this measurement report."
::= { dot11FrameReportEntry 4 }
dot11FrameRprtOperatingClass OBJECT-TYPE
SYNTAX Unsigned32(1..255)
MAX-ACCESS read-only
STATUS current
DESCRIPTION
"This is a status variable.
It is written by the SME when a measurement report is completed.
This attribute indicates the channel set for this measurement report.
Country, Operating Class and Channel Number together specify the channel
frequency and spacing for this measurement report. Valid values of Operating
Class are shown in Annex E."
REFERENCE "Annex E"
::= { dot11FrameReportEntry 5 }
dot11FrameRprtActualStartTime OBJECT-TYPE
SYNTAX TSFType
MAX-ACCESS read-only
STATUS current
DESCRIPTION
"This is a status variable.
It is written by the SME when a measurement report is completed.
This attribute indicates the TSF value at the time when measurement
started."
::= { dot11FrameReportEntry 6 }
dot11FrameRprtMeasurementDuration OBJECT-TYPE
SYNTAX Unsigned32
MAX-ACCESS read-only
STATUS current
DESCRIPTION
"This is a status variable.
It is written by the SME when a measurement report is completed.
This attribute indicates the duration over which the Frame Report was measured,
expressed in units of TUs."
::= { dot11FrameReportEntry 7 }
dot11FrameRprtTransmitSTAAddress OBJECT-TYPE
SYNTAX MacAddress
MAX-ACCESS read-only
STATUS current
DESCRIPTION
"This is a status variable.
It is written by the SME when a measurement report is completed.
The MAC address of STA for this row of Frame report that it has been
received from."
::= { dot11FrameReportEntry 8 }
dot11FrameRprtBSSID OBJECT-TYPE
SYNTAX MacAddress
MAX-ACCESS read-only
STATUS current
DESCRIPTION
"This is a status variable.
It is written by the SME when a measurement report is completed.
This attribute indicates the BSSID of the STA that transmitted this
frame."
::= { dot11FrameReportEntry 9 }
dot11FrameRprtPhyType OBJECT-TYPE
SYNTAX INTEGER {
fhss(1),
dsss(2),
irbaseband(3),
ofdm(4),
hrdsss(5),
erp(6),
ht(7) }
UNITS "dot11PHYType"
MAX-ACCESS read-create
STATUS current
DESCRIPTION
"This is a status variable.
It is written by the SME when a measurement report is completed.
This attribute indicates the PHY used for frame reception in this row of
the frame report."
::= { dot11FrameReportEntry 10 }
dot11FrameRprtAvgRCPI OBJECT-TYPE
SYNTAX Unsigned32(0..255)
MAX-ACCESS read-only
STATUS current
DESCRIPTION
"This is a status variable.
It is written by the SME when a measurement report is completed.
This attribute indicates the average value for the received channel power
of all the frames received and counted in this Frame Report Entry, in dBm,
as defined in the RCPI measurement subclause for the indicated PHY Type.
RCPIval = Int[(RCPIpower in dBm + 110)*2], for RCPI in the range -110 dBm
to 0 dBm. RCPIval = 220 for RCPI > 0 dBm. RCPIval = 255 when RCPI is not
available."
::= { dot11FrameReportEntry 11 }
dot11FrameRprtLastRSNI OBJECT-TYPE
SYNTAX Unsigned32(0..255)
MAX-ACCESS read-only
STATUS current
DESCRIPTION
"This is a status variable.
It is written by the SME when a measurement report is completed.
This attribute indicates the received signal to noise ratio of the
received frame in dBm. RSNI is the received signal to noise plus interference
ratio derived from the RCPI for the received frame and from the most
recent ANPI value measured on the channel used to receive the frame. RSNI
may be calculated by the ratio of the received signal power (RCPI - ANPI)
over the noise plus interference power (ANPI) where RSNI = [(ratio(dB) +
10) * 2], for ratios in the range -10dB to +118dB. Other measurement
techniques are allowed."
::= { dot11FrameReportEntry 12 }
dot11FrameRprtLastRCPI OBJECT-TYPE
SYNTAX Unsigned32(0..255)
MAX-ACCESS read-only
STATUS current
DESCRIPTION
"This is a status variable.
It is written by the SME when a measurement report is completed.
This attribute indicates the received channel power of the most recently
measured frame in this Frame Report entry, in dBm, as defined in the RCPI
measurement subclause for the indicated PHY Type.
RCPIval = Int[(RCPIpower in dBm + 110)*2], for RCPI in the range -110 dBm
to 0 dBm. RCPIval = 220 for RCPI > 0 dBm. RCPIval = 255 when RCPI is not
available."
::= { dot11FrameReportEntry 13 }
dot11FrameRprtAntennaID OBJECT-TYPE
SYNTAX Unsigned32(0..255)
MAX-ACCESS read-only
STATUS current
DESCRIPTION
"This is a status variable.
It is written by the SME when a measurement report is completed.
This attribute indicates the identifying number for the antenna used for
this measurement. The value 0 indicates that the antenna identifier is
unknown. The value 255 indicates that this measurement was made with multiple
antennas. The value 1 is used for a STA with only one antenna. STAs
with more than one antenna assign Antenna IDs to each antenna as consecutive,
ascending numbers. Each Antenna ID number represents a unique
antenna characterized by a fixed relative position, a fixed relative
direction, and a peak gain for that position and direction."
::= { dot11FrameReportEntry 14 }
dot11FrameRprtNumberFrames OBJECT-TYPE
SYNTAX Unsigned32(0..65535)
MAX-ACCESS read-only
STATUS current
DESCRIPTION
"This is a status variable.
It is written by the SME when a measurement report is completed.
This attribute indicates the number of received frames in the Measurement
Report frame for this row of the Frame Report."
::= { dot11FrameReportEntry 15 }
dot11FrameRprtVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11FrameReportEntry 16 }
dot11FrameRptMeasurementMode OBJECT-TYPE
SYNTAX INTEGER {
success(0),
incapableBit(1),
refusedBit(2) }
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11FrameReportEntry 17 }
-- ********************************************************************
-- * End of dot11FrameReport TABLE
-- ********************************************************************
-- ********************************************************************
-- * dot11STAStatisticsReport TABLE
-- ********************************************************************
dot11STAStatisticsReportTable OBJECT-TYPE
SYNTAX SEQUENCE OF Dot11STAStatisticsReportEntry
MAX-ACCESS not-accessible
STATUS current
DESCRIPTION
"This table contains the current list of STA Statistics reports that have
been received by the MLME. The report tables are maintained as a FIFO to
preserve freshness, thus the rows in this table can be deleted for memory
constraints or other implementation constraints determined by the vendor.
New rows have different RprtIndex values than those deleted within the
range limitation of the index. One easy way is to monotonically increase
RprtIndex for new reports being written in the table."
::= { dot11RMReport 5 }
dot11STAStatisticsReportEntry OBJECT-TYPE
SYNTAX Dot11STAStatisticsReportEntry
MAX-ACCESS not-accessible
STATUS current
DESCRIPTION
"An entry in the dot11STAStatisticsReportTable Indexed by
dot11STAStatisticsReportIndex."
INDEX { dot11STAStatisticsReportIndex }
::= { dot11STAStatisticsReportTable 1 }
Dot11STAStatisticsReportEntry ::=
SEQUENCE {
dot11STAStatisticsReportIndex Unsigned32,
dot11STAStatisticsReportToken OCTET STRING,
dot11STAStatisticsIfIndex InterfaceIndex,
dot11STAStatisticsSTAAddress MacAddress,
dot11STAStatisticsMeasurementDuration Unsigned32,
dot11STAStatisticsGroupID INTEGER,
dot11STAStatisticsTransmittedFragmentCount Counter32,
dot11STAStatisticsGroupTransmittedFrameCount Counter32,
dot11STAStatisticsFailedCount Counter32,
dot11STAStatisticsRetryCount Counter32,
dot11STAStatisticsMultipleRetryCount Counter32,
dot11STAStatisticsFrameDuplicateCount Counter32,
dot11STAStatisticsRTSSuccessCount Counter32,
dot11STAStatisticsRTSFailureCount Counter32,
dot11STAStatisticsACKFailureCount Counter32,
dot11STAStatisticsQosTransmittedFragmentCount Counter32,
dot11STAStatisticsQosFailedCount Counter32,
dot11STAStatisticsQosRetryCount Counter32,
dot11STAStatisticsQosMultipleRetryCount Counter32,
dot11STAStatisticsQosFrameDuplicateCount Counter32,
dot11STAStatisticsQosRTSSuccessCount Counter32,
dot11STAStatisticsQosRTSFailureCount Counter32,
dot11STAStatisticsQosACKFailureCount Counter32,
dot11STAStatisticsQosReceivedFragmentCount Counter32,
dot11STAStatisticsQosTransmittedFrameCount Counter32,
dot11STAStatisticsQosDiscardedFrameCount Counter32,
dot11STAStatisticsQosMPDUsReceivedCount Counter32,
dot11STAStatisticsQosRetriesReceivedCount Counter32,
dot11STAStatisticsReceivedFragmentCount Counter32,
dot11STAStatisticsGroupReceivedFrameCount Counter32,
dot11STAStatisticsFCSErrorCount Counter32,
dot11STAStatisticsTransmittedFrameCount Counter32,
dot11STAStatisticsAPAverageAccessDelay Unsigned32,
dot11STAStatisticsAverageAccessDelayBestEffort Unsigned32,
dot11STAStatisticsAverageAccessDelayBackground Unsigned32,
dot11STAStatisticsAverageAccessDelayVideo Unsigned32,
dot11STAStatisticsAverageAccessDelayVoice Unsigned32,
dot11STAStatisticsStationCount Unsigned32,
dot11STAStatisticsChannelUtilization Unsigned32,
dot11STAStatisticsVendorSpecific OCTET STRING,
dot11STAStatisticsRprtMeasurementMode INTEGER,
dot11STAStatisticsRSNAStatsCMACICVErrors Counter32,
dot11STAStatisticsRSNAStatsCMACReplays Counter32,
dot11STAStatisticsRSNAStatsRobustMgmtCCMPReplays Counter32,
dot11STAStatisticsRSNAStatsTKIPICVErrors Counter32,
dot11STAStatisticsRSNAStatsTKIPReplays Counter32,
dot11STAStatisticsRSNAStatsCCMPDecryptErrors Counter32,
dot11STAStatisticsRSNAStatsCCMPReplays Counter32,
dot11STAStatisticsReportingReasonSTACounters OCTET STRING,
dot11STAStatisticsReportingReasonQosCounters OCTET STRING,
dot11STAStatisticsReportingReasonRsnaCounters OCTET STRING,
dot11STAStatisticsTransmittedAMSDUCount Counter32,
dot11STAStatisticsFailedAMSDUCount Counter32,
dot11STAStatisticsRetryAMSDUCount Counter32,
dot11STAStatisticsMultipleRetryAMSDUCount Counter32,
dot11STAStatisticsTransmittedOctetsInAMSDUCount Counter64,
dot11STAStatisticsAMSDUAckFailureCount Counter32,
dot11STAStatisticsReceivedAMSDUCount Counter32,
dot11STAStatisticsReceivedOctetsInAMSDUCount Counter64,
dot11STAStatisticsTransmittedAMPDUCount Counter32,
dot11STAStatisticsTransmittedMPDUsInAMPDUCount Counter32,
dot11STAStatisticsTransmittedOctetsInAMPDUCount Counter64,
dot11STAStatisticsAMPDUReceivedCount Counter32,
dot11STAStatisticsMPDUInReceivedAMPDUCount Counter32,
dot11STAStatisticsReceivedOctetsInAMPDUCount Counter64,
dot11STAStatisticsAMPDUDelimiterCRCErrorCount Counter32,
dot11STAStatisticsImplicitBARFailureCount Counter32,
dot11STAStatisticsExplicitBARFailureCount Counter32,
dot11STAStatisticsChannelWidthSwitchCount Counter32,
dot11STAStatisticsTwentyMHzFrameTransmittedCount Counter32,
dot11STAStatisticsFortyMHzFrameTransmittedCount Counter32,
dot11STAStatisticsTwentyMHzFrameReceivedCount Counter32,
dot11STAStatisticsFortyMHzFrameReceivedCount Counter32,
dot11STAStatisticsPSMPUTTGrantDuration Counter32,
dot11STAStatisticsPSMPUTTUsedDuration Counter32,
dot11STAStatisticsGrantedRDGUsedCount Counter32,
dot11STAStatisticsGrantedRDGUnusedCount Counter32,
dot11STAStatisticsTransmittedFramesInGrantedRDGCount Counter32,
dot11STAStatisticsTransmittedOctetsInGrantedRDGCount Counter64,
dot11STAStatisticsDualCTSSuccessCount Counter32,
dot11STAStatisticsDualCTSFailureCount Counter32,
dot11STAStatisticsRTSLSIGSuccessCount Counter32,
dot11STAStatisticsRTSLSIGFailureCount Counter32,
dot11STAStatisticsBeamformingFrameCount Counter32,
dot11STAStatisticsSTBCCTSSuccessCount Counter32,
dot11STAStatisticsSTBCCTSFailureCount Counter32,
dot11STAStatisticsnonSTBCCTSSuccessCount Counter32,
dot11STAStatisticsnonSTBCCTSFailureCount Counter32
}
dot11STAStatisticsReportIndex OBJECT-TYPE
SYNTAX Unsigned32
MAX-ACCESS not-accessible
STATUS current
DESCRIPTION
"Index for STA Statistics Report elements in
dot11STAStatisticsReportTable, greater than 0."
::= { dot11STAStatisticsReportEntry 1 }
dot11STAStatisticsReportToken OBJECT-TYPE
SYNTAX OCTET STRING
MAX-ACCESS read-only
STATUS current
DESCRIPTION
"This is a status variable.
It is written by the SME when a measurement report is completed.
This attribute indicates the token that was indicated in the measurement
request that generated this measurement report. This should be an exact
match to the original dot11RMRqstToken attribute. Note that there may be
multiple entries in the table that match this value since a single request
may generate multiple measurement reports."
::= { dot11STAStatisticsReportEntry 2 }
dot11STAStatisticsIfIndex OBJECT-TYPE
SYNTAX InterfaceIndex
MAX-ACCESS read-only
STATUS current
DESCRIPTION
"This is a status variable.
It is written by the SME when a measurement report is completed.
Identifies the Interface that this row of STA Statistics Report has been
received on"
::= { dot11STAStatisticsReportEntry 3 }
dot11STAStatisticsSTAAddress OBJECT-TYPE
SYNTAX MacAddress
MAX-ACCESS read-only
STATUS current
DESCRIPTION
"This is a status variable.
It is written by the SME when a measurement report is completed.
The MAC address of the STA that returned this STA Statistics Report."
::= { dot11STAStatisticsReportEntry 4 }
dot11STAStatisticsMeasurementDuration OBJECT-TYPE
SYNTAX Unsigned32
UNITS "TUs"
MAX-ACCESS read-only
STATUS current
DESCRIPTION
"This is a status variable.
It is written by the SME when a measurement report is completed.
This attribute indicates the duration over which the STA Statistics was
measured. The value 0 for this attribute indicates that the reported statistics
are a current snapshot of the statistics variables. A nonzero
value for this attribute indicates that the reported statistics contain
the difference in the corresponding statistics variables over the indicated
duration."
::= { dot11STAStatisticsReportEntry 5 }
dot11STAStatisticsGroupID OBJECT-TYPE
SYNTAX INTEGER {
dot11CountersTable(0),
dot11MacStatistics(1),
dot11QosCountersTableforUP0(2),
dot11QosCountersTableforUP1(3),
dot11QosCountersTableforUP2(4),
dot11QosCountersTableforUP3(5),
dot11QosCountersTableforUP4(6),
dot11QosCountersTableforUP5(7),
dot11QosCountersTableforUP6(8),
dot11QosCountersTableforUP7(9),
bSSAverageAccessDelays(10),
dot11CountersGroup3Tablefor31(11),
dot11CountersGroup3Tablefor32(12),
dot11CountersGroup3Tablefor33(13),
dot11CountersGroup3Tablefor34(14),
dot11CountersGroup3Tablefor35(15),
dot11RSNAStatsTable(16) }
MAX-ACCESS read-only
STATUS current
DESCRIPTION
"This is a status variable.
It is written by the SME when a measurement report is completed.
This attribute indicates the value of dot11RMRqstSTAStatRqstGroupID
returned from the STA in this STA Statistics Report."
DEFVAL { 0 }
::= { dot11STAStatisticsReportEntry 6 }
dot11STAStatisticsTransmittedFragmentCount OBJECT-TYPE
SYNTAX Counter32
MAX-ACCESS read-only
STATUS current
DESCRIPTION
"This is a status variable.
It is written by the SME when a measurement report is completed.
If dot11STAStatisticsMeasurementDuration is 0, this attribute indicates
the value of dot11TransmittedFragmentCount returned from the STA in this
STA Statistics Report. If dot11STAStatisticsMeasurementDuration indicates
a nonzero value, this attribute indicates the difference in the referenced
dot11 variable over the indicated duration. This attribute is only valid
if the dot11STAStatisticsGroupID is 0, and is ignored otherwise."
::= { dot11STAStatisticsReportEntry 7 }
dot11STAStatisticsGroupTransmittedFrameCount OBJECT-TYPE
SYNTAX Counter32
MAX-ACCESS read-only
STATUS current
DESCRIPTION
"This is a status variable.
It is written by the SME when a measurement report is completed.
If dot11STAStatisticsMeasurementDuration is 0, this attribute indicates
the value of dot11GroupTransmittedFrameCount returned from the STA in this
STA Statistics Report. If dot11STAStatisticsMeasurementDuration indicates
a nonzero value, this attribute indicates the difference in the referenced
dot11 variable over the indicated duration. This attribute is only valid
if the dot11STAStatisticsGroupID is 0, and is ignored otherwise."
::= { dot11STAStatisticsReportEntry 8 }
dot11STAStatisticsFailedCount OBJECT-TYPE
SYNTAX Counter32
MAX-ACCESS read-only
STATUS current
DESCRIPTION
"This is a status variable.
It is written by the SME when a measurement report is completed.
If dot11STAStatisticsMeasurementDuration is 0, this attribute indicates
the value of dot11FailedCount returned from the STA in this STA Statistics
Report. If dot11STAStatisticsMeasurementDuration indicates a nonzero
value, this attribute indicates the difference in the referenced dot11
variable over the indicated duration. This attribute is only valid if the
dot11STAStatisticsGroupID is 0, and is ignored otherwise."
::= { dot11STAStatisticsReportEntry 9 }
dot11STAStatisticsRetryCount OBJECT-TYPE
SYNTAX Counter32
MAX-ACCESS read-only
STATUS current
DESCRIPTION
"This is a status variable.
It is written by the SME when a measurement report is completed.
If dot11STAStatisticsMeasurementDuration is 0, this attribute indicates
the value of dot11RetryCount returned from the STA in this STA Statistics
Report. If dot11STAStatisticsMeasurementDuration indicates a nonzero
value, this attribute indicates the difference in the referenced dot11
variable over the indicated duration. This attribute is only valid if the
dot11STAStatisticsGroupID is 1, and is ignored otherwise."
::= { dot11STAStatisticsReportEntry 10 }
dot11STAStatisticsMultipleRetryCount OBJECT-TYPE
SYNTAX Counter32
MAX-ACCESS read-only
STATUS current
DESCRIPTION
"This is a status variable.
It is written by the SME when a measurement report is completed.
If dot11STAStatisticsMeasurementDuration is 0, this attribute indicates
the value of dot11MultipleRetryCount returned from the STA in this STA
Statistics Report. If dot11STAStatisticsMeasurementDuration indicates a
nonzero value, this attribute indicates the difference in the referenced
dot11 variable over the indicated duration. This attribute is only valid
if the dot11STAStatisticsGroupID is 1, and is ignored otherwise."
::= { dot11STAStatisticsReportEntry 11 }
dot11STAStatisticsFrameDuplicateCount OBJECT-TYPE
SYNTAX Counter32
MAX-ACCESS read-only
STATUS current
DESCRIPTION
"This is a status variable.
It is written by the SME when a measurement report is completed.
If dot11STAStatisticsMeasurementDuration is 0, this attribute indicates
the value of dot11FrameDuplicateCount returned from the STA in this STA
Statistics Report. If dot11STAStatisticsMeasurementDuration indicates a
nonzero value, this attribute indicates the difference in the referenced
dot11 variable over the indicated duration. This attribute is only valid
if the dot11STAStatisticsGroupID is 1, and is ignored otherwise."
::= { dot11STAStatisticsReportEntry 12 }
dot11STAStatisticsRTSSuccessCount OBJECT-TYPE
SYNTAX Counter32
MAX-ACCESS read-only
STATUS current
DESCRIPTION
"This is a status variable.
It is written by the SME when a measurement report is completed.
If dot11STAStatisticsMeasurementDuration is 0, this attribute indicates
the value of dot11RTSSuccessCount returned from the STA in this STA Statistics
Report. If dot11STAStatisticsMeasurementDuration indicates a nonzero
value, this attribute indicates the difference in the referenced
dot11 variable over the indicated duration. This attribute is only valid
if the dot11STAStatisticsGroupID is 1, and is ignored otherwise."
::= { dot11STAStatisticsReportEntry 13 }
dot11STAStatisticsRTSFailureCount OBJECT-TYPE
SYNTAX Counter32
MAX-ACCESS read-only
STATUS current
DESCRIPTION
"This is a status variable.
It is written by the SME when a measurement report is completed.
If dot11STAStatisticsMeasurementDuration is 0, this attribute indicates
the value of dot11RTSFailureCount returned from the STA in this STA Statistics
Report. If dot11STAStatisticsMeasurementDuration indicates a nonzero
value, this attribute indicates the difference in the referenced
dot11 variable over the indicated duration. This attribute is only valid
if the dot11STAStatisticsGroupID is 1, and is ignored otherwise."
::= { dot11STAStatisticsReportEntry 14 }
dot11STAStatisticsACKFailureCount OBJECT-TYPE
SYNTAX Counter32
MAX-ACCESS read-only
STATUS current
DESCRIPTION
"This is a status variable.
It is written by the SME when a measurement report is completed.
If dot11STAStatisticsMeasurementDuration is 0, this attribute indicates
the value of dot11ACKFailureCount returned from the STA in this STA Statistics
Report. If dot11STAStatisticsMeasurementDuration indicates a nonzero
value, this attribute indicates the difference in the referenced
dot11 variable over the indicated duration. This attribute is only valid
if the dot11STAStatisticsGroupID is 1, and is ignored otherwise."
::= { dot11STAStatisticsReportEntry 15 }
dot11STAStatisticsQosTransmittedFragmentCount OBJECT-TYPE
SYNTAX Counter32
MAX-ACCESS read-only
STATUS current
DESCRIPTION
"This is a status variable.
It is written by the SME when a measurement report is completed.
If dot11STAStatisticsMeasurementDuration is 0, this attribute indicates
the value of dot11QosTransmittedFragmentCount returned from the STA in
this STA Statistics Report. If dot11STAStatisticsMeasurementDuration indicates
a nonzero value, this attribute indicates the difference in the referenced
dot11 variable over the indicated duration. This attribute is only
valid if the dot11STAStatisticsGroupID is 2-9, and is ignored otherwise."
::= { dot11STAStatisticsReportEntry 16 }
dot11STAStatisticsQosFailedCount OBJECT-TYPE
SYNTAX Counter32
MAX-ACCESS read-only
STATUS current
DESCRIPTION
"This is a status variable.
It is written by the SME when a measurement report is completed.
If dot11STAStatisticsMeasurementDuration is 0, this attribute indicates
the value of dot11QosFailedCount returned from the STA in this STA Statistics
Report. If dot11STAStatisticsMeasurementDuration indicates a nonzero
value, this attribute indicates the difference in the referenced dot11
variable over the indicated duration. This attribute is only valid if the
dot11STAStatisticsGroupID is 2-9, and is ignored otherwise."
::= { dot11STAStatisticsReportEntry 17 }
dot11STAStatisticsQosRetryCount OBJECT-TYPE
SYNTAX Counter32
MAX-ACCESS read-only
STATUS current
DESCRIPTION
"This is a status variable.
It is written by the SME when a measurement report is completed.
If dot11STAStatisticsMeasurementDuration is 0, this attribute indicates
the value of dot11QosRetryCount returned from the STA in this STA Statistics
Report. If dot11STAStatisticsMeasurementDuration indicates a nonzero
value, this attribute indicates the difference in the referenced dot11
variable over the indicated duration. This attribute is only valid if the
dot11STAStatisticsGroupID is 2-9, and is ignored otherwise."
::= { dot11STAStatisticsReportEntry 18 }
dot11STAStatisticsQosMultipleRetryCount OBJECT-TYPE
SYNTAX Counter32
MAX-ACCESS read-only
STATUS current
DESCRIPTION
"This is a status variable.
It is written by the SME when a measurement report is completed.
If dot11STAStatisticsMeasurementDuration is 0, this attribute indicates
the value of dot11QosMultipleRetryCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 19 }
dot11STAStatisticsQosFrameDuplicateCount OBJECT-TYPE
SYNTAX Counter32
MAX-ACCESS read-only
STATUS current
DESCRIPTION
"This is a status variable.
It is written by the SME when a measurement report is completed.
If dot11STAStatisticsMeasurementDuration is 0, this attribute indicates
the value of dot11QosFrameDuplicateCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 20 }
dot11STAStatisticsQosRTSSuccessCount OBJECT-TYPE
SYNTAX Counter32
MAX-ACCESS read-only
STATUS current
DESCRIPTION
"This is a status variable.
It is written by the SME when a measurement report is completed.
If dot11STAStatisticsMeasurementDuration is 0, this attribute indicates
the value of dot11QosRTSSuccessCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 21 }
dot11STAStatisticsQosRTSFailureCount OBJECT-TYPE
SYNTAX Counter32
MAX-ACCESS read-only
STATUS current
DESCRIPTION
"This is a status variable.
It is written by the SME when a measurement report is completed.
If dot11STAStatisticsMeasurementDuration is 0, this attribute indicates
the value of dot11QosRTSFailureCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 22 }
dot11STAStatisticsQosACKFailureCount OBJECT-TYPE
SYNTAX Counter32
MAX-ACCESS read-only
STATUS current
DESCRIPTION
"This is a status variable.
It is written by the SME when a measurement report is completed.
If dot11STAStatisticsMeasurementDuration is 0, this attribute indicates
the value of dot11QosACKFailureCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 23 }
dot11STAStatisticsQosReceivedFragmentCount OBJECT-TYPE
SYNTAX Counter32
MAX-ACCESS read-only
STATUS current
DESCRIPTION
"This is a status variable.
It is written by the SME when a measurement report is completed.
If dot11STAStatisticsMeasurementDuration is 0, this attribute indicates
the value of dot11QosReceivedFragmentCount returned from the STA in this
STA Statistics Report. If dot11STAStatisticsMeasurementDuration indicates
a nonzero value, this attribute indicates the difference in the referenced
dot11 variable over the indicated duration. This attribute is only valid
if the dot11STAStatisticsGroupID is 2-9, and is ignored otherwise."
::= { dot11STAStatisticsReportEntry 24 }
dot11STAStatisticsQosTransmittedFrameCount OBJECT-TYPE
SYNTAX Counter32
MAX-ACCESS read-only
STATUS current
DESCRIPTION
"This is a status variable.
It is written by the SME when a measurement report is completed.
If dot11STAStatisticsMeasurementDuration is 0, this attribute indicates
the value of dot11QosTransmittedFrameCount returned from the STA in this
STA Statistics Report. If dot11STAStatisticsMeasurementDuration indicates
a nonzero value, this attribute indicates the difference in the referenced
dot11 variable over the indicated duration. This attribute is only valid
if the dot11STAStatisticsGroupID is 2-9, and is ignored otherwise."
::= { dot11STAStatisticsReportEntry 25 }
dot11STAStatisticsQosDiscardedFrameCount OBJECT-TYPE
SYNTAX Counter32
MAX-ACCESS read-only
STATUS current
DESCRIPTION
"This is a status variable.
It is written by the SME when a measurement report is completed.
If dot11STAStatisticsMeasurementDuration is 0, this attribute indicates
the value of dot11QosDiscardedFrameCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 26 }
dot11STAStatisticsQosMPDUsReceivedCount OBJECT-TYPE
SYNTAX Counter32
MAX-ACCESS read-only
STATUS current
DESCRIPTION
"This is a status variable.
It is written by the SME when a measurement report is completed.
If dot11STAStatisticsMeasurementDuration is 0, this attribute indicates
the value of dot11QosMPDUsReceivedCount returned from the STA in this STA
Statistics Report. If dot11STAStatisticsMeasurementDuration indicates a
nonzero value, this attribute indicates the difference in the referenced
dot11 variable over the indicated duration. This attribute is only valid
if the dot11STAStatisticsGroupID is 2-9, and is ignored otherwise."
::= { dot11STAStatisticsReportEntry 27 }
dot11STAStatisticsQosRetriesReceivedCount OBJECT-TYPE
SYNTAX Counter32
MAX-ACCESS read-only
STATUS current
DESCRIPTION
"This is a status variable.
It is written by the SME when a measurement report is completed.
If dot11STAStatisticsMeasurementDuration is 0, this attribute indicates
the value of dot11QosRetriesReceivedCount returned from the STA in this
STA Statistics Report. If dot11STAStatisticsMeasurementDuration indicates
a nonzero value, this attribute indicates the difference in the referenced
dot11 variable over the indicated duration. This attribute is only valid
if the dot11STAStatisticsGroupID is 2-9, and is ignored otherwise."
::= { dot11STAStatisticsReportEntry 28 }
dot11STAStatisticsReceivedFragmentCount OBJECT-TYPE
SYNTAX Counter32
MAX-ACCESS read-only
STATUS current
DESCRIPTION
"This is a status variable.
It is written by the SME when a measurement report is completed.
If dot11STAStatisticsMeasurementDuration is 0, this attribute indicates
the value of dot11ReceivedFragmentCount returned from the STA in this STA
Statistics Report. If dot11STAStatisticsMeasurementDuration indicates a
nonzero value, this attribute indicates the difference in the referenced
dot11 variable over the indicated duration. This attribute is only valid
if the dot11STAStatisticsGroupID is 0, and is ignored otherwise."
::= { dot11STAStatisticsReportEntry 29 }
dot11STAStatisticsGroupReceivedFrameCount OBJECT-TYPE
SYNTAX Counter32
MAX-ACCESS read-only
STATUS current
DESCRIPTION
"This is a status variable.
It is written by the SME when a measurement report is completed.
If dot11STAStatisticsMeasurementDuration is 0, this attribute indicates
the value of dot11GroupReceivedFrameCount returned from the STA in this
STA Statistics Report. If dot11STAStatisticsMeasurementDuration indicates
a nonzero value, this attribute indicates the difference in the referenced
dot11 variable over the indicated duration. This attribute is only valid
if the dot11STAStatisticsGroupID is 0, and is ignored otherwise."
::= { dot11STAStatisticsReportEntry 30 }
dot11STAStatisticsFCSErrorCount OBJECT-TYPE
SYNTAX Counter32
MAX-ACCESS read-only
STATUS current
DESCRIPTION
"This is a status variable.
It is written by the SME when a measurement report is completed.
If dot11STAStatisticsMeasurementDuration is 0, this attribute indicates
the value of dot11FCSErrorCount returned from the STA in this STA Statistics
Report. If dot11STAStatisticsMeasurementDuration indicates a nonzero
value, this attribute indicates the difference in the referenced dot11
variable over the indicated duration. This attribute is only valid if the
dot11STAStatisticsGroupID is 0, and is ignored otherwise."
::= { dot11STAStatisticsReportEntry 31 }
dot11STAStatisticsTransmittedFrameCount OBJECT-TYPE
SYNTAX Counter32
MAX-ACCESS read-only
STATUS current
DESCRIPTION
"This is a status variable.
It is written by the SME when a measurement report is completed.
If dot11STAStatisticsMeasurementDuration is 0, this attribute indicates
the value of dot11TransmittedFrameCount returned from the STA in this STA
Statistics Report. If dot11STAStatisticsMeasurementDuration indicates a
nonzero value, this attribute indicates the difference in the referenced
dot11 variable over the indicated duration. This attribute is only valid
if the dot11STAStatisticsGroupID is 0, and is ignored otherwise."
::= { dot11STAStatisticsReportEntry 32 }
dot11STAStatisticsAPAverageAccessDelay OBJECT-TYPE
SYNTAX Unsigned32 (0..255)
MAX-ACCESS read-only
STATUS current
DESCRIPTION
"This is a status variable.
It is written by the SME when a measurement report is completed.
If dot11STAStatisticsMeasurementDuration is 0, this attribute indicates
the value of the AP Average Access Delay (AAD) returned from the STA in
this STA Statistics Report. If dot11STAStatisticsMeasurementDuration indicates
a nonzero value, this attribute indicates the difference in the referenced
access delay value over the indicated duration. This attribute is
only valid if the dot11STAStatisticsGroupID is 10, and is ignored otherwise."
REFERENCE
"IEEE 802.11 8.4.2.41"
::= { dot11STAStatisticsReportEntry 33 }
dot11STAStatisticsAverageAccessDelayBestEffort OBJECT-TYPE
SYNTAX Unsigned32 (0..255)
MAX-ACCESS read-only
STATUS current
DESCRIPTION
"This is a status variable.
It is written by the SME when a measurement report is completed.
If dot11STAStatisticsMeasurementDuration is 0, this attribute indicates
the value of the Average Access Delay (AAD) for the Best Effort Access
Category returned from the STA in this STA Statistics Report. If
dot11STAStatisticsMeasurementDuration indicates a nonzero value, this
attribute indicates the difference in the referenced access delay value
over the indicated duration. This attribute is only valid if the
dot11STAStatisticsGroupID is 10, and is ignored otherwise."
REFERENCE
"IEEE 802.11 8.4.2.46"
::= { dot11STAStatisticsReportEntry 34 }
dot11STAStatisticsAverageAccessDelayBackground OBJECT-TYPE
SYNTAX Unsigned32 (0..255)
MAX-ACCESS read-only
STATUS current
DESCRIPTION
"This is a status variable.
It is written by the SME when a measurement report is completed.
If dot11STAStatisticsMeasurementDuration is 0, this attribute indicates
the value of the Average Access Delay (AAD) for the Background Access Category
returned from the STA in this STA Statistics Report. If
dot11STAStatisticsMeasurementDuration indicates a nonzero value, this
attribute indicates the difference in the referenced access delay value
over the indicated duration. This attribute is only valid if the
dot11STAStatisticsGroupID is 10, and is ignored otherwise."
REFERENCE
"IEEE 802.11 8.4.2.46"
::= { dot11STAStatisticsReportEntry 35 }
dot11STAStatisticsAverageAccessDelayVideo OBJECT-TYPE
SYNTAX Unsigned32 (0..255)
MAX-ACCESS read-only
STATUS current
DESCRIPTION
"This is a status variable.
It is written by the SME when a measurement report is completed.
If dot11STAStatisticsMeasurementDuration is 0, this attribute indicates
the value of the Average Access Delay (AAD) for the Video Access Category
returned from the STA in this STA Statistics Report. If
dot11STAStatisticsMeasurementDuration indicates a nonzero value, this
attribute indicates the difference in the referenced access delay value
over the indicated duration. This attribute is only valid if the
dot11STAStatisticsGroupID is 10, and is ignored otherwise."
REFERENCE
"IEEE 802.11 8.4.2.46"
::= { dot11STAStatisticsReportEntry 36 }
dot11STAStatisticsAverageAccessDelayVoice OBJECT-TYPE
SYNTAX Unsigned32 (0..255)
MAX-ACCESS read-only
STATUS current
DESCRIPTION
"This is a status variable.
It is written by the SME when a measurement report is completed.
If dot11STAStatisticsMeasurementDuration is 0, this attribute indicates
the value of the Average Access Delay (AAD) for the Voice Access Category
returned from the STA in this STA Statistics Report. If
dot11STAStatisticsMeasurementDuration indicates a nonzero value, this
attribute indicates the difference in the referenced access delay value
over the indicated duration. This attribute is only valid if the
dot11STAStatisticsGroupID is 10, and is ignored otherwise."
REFERENCE
"IEEE 802.11 8.4.2.46"
::= { dot11STAStatisticsReportEntry 37 }
dot11STAStatisticsStationCount OBJECT-TYPE
SYNTAX Unsigned32 (0..65535)
MAX-ACCESS read-only
STATUS current
DESCRIPTION
"This is a status variable.
It is written by the SME when a measurement report is completed.
If dot11STAStatisticsMeasurementDuration is 0, this attribute indicates
the value of dot11AssociatedStationCount returned from the STA in this STA
Statistics Report. If dot11STAStatisticsMeasurementDuration indicates a
nonzero value, this attribute indicates the difference in the referenced
dot11 variable over the indicated duration. This attribute is only valid
if the dot11STAStatisticsGroupID is 10, and is ignored otherwise."
::= { dot11STAStatisticsReportEntry 38 }
dot11STAStatisticsChannelUtilization OBJECT-TYPE
SYNTAX Unsigned32 (0..255)
UNITS "1/255"
MAX-ACCESS read-only
STATUS current
DESCRIPTION
"This is a status variable.
It is written by the SME when a measurement report is completed.
If dot11STAStatisticsMeasurementDuration is 0, this attribute indicates
the value of the Channel Utilization returned from the STA in this STA
Statistics Report. If dot11STAStatisticsMeasurementDuration indicates a
nonzero value, this attribute indicates the difference in the Channel Utilization
value over the indicated duration. The Channel Utilization is the
time fraction during which the AP sensed the channel busy. This attribute
is only valid if the dot11STAStatisticsGroupID is 10, and is ignored otherwise."
REFERENCE
"IEEE 802.11 8.4.2.30"
::= { dot11STAStatisticsReportEntry 39 }
dot11STAStatisticsVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11STAStatisticsReportEntry 40 }
dot11STAStatisticsRprtMeasurementMode OBJECT-TYPE
SYNTAX INTEGER {
success(0),
incapableBit(1),
refusedBit(2)
}
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11STAStatisticsReportEntry 41 }
dot11STAStatisticsRSNAStatsCMACICVErrors OBJECT-TYPE
SYNTAX Counter32
MAX-ACCESS read-only
STATUS current
DESCRIPTION
"This is a status variable.
It is written by the SME when a measurement report is completed.
If dot11STAStatisticsMeasurementDuration is 0, this attribute indicates
the value of dot11RSNAStatsCMACICVErrors returned from the STA in this STA
Statistics Report. If dot11STAStatisticsMeasurementDuration indicates a
nonzero value, this attribute indicates the difference in the referenced
dot11 variable over the indicated duration. This attribute is only valid
if the dot11STAStatisticsGroupID is 16, and is ignored otherwise."
::= { dot11STAStatisticsReportEntry 42 }
dot11STAStatisticsRSNAStatsCMACReplays OBJECT-TYPE
SYNTAX Counter32
MAX-ACCESS read-only
STATUS current
DESCRIPTION
"This is a status variable.
It is written by the SME when a measurement report is completed.
If dot11STAStatisticsMeasurementDuration is 0, this attribute indicates
the value of dot11RSNAStatsCMACReplays returned from the STA in this STA
Statistics Report. If dot11STAStatisticsMeasurementDuration indicates a
nonzero value, this attribute indicates the difference in the referenced
dot11 variable over the indicated duration. This attribute is only valid
if the dot11STAStatisticsGroupID is 16, and is ignored otherwise."
::= { dot11STAStatisticsReportEntry 43 }
dot11STAStatisticsRSNAStatsRobustMgmtCCMPReplays OBJECT-TYPE
SYNTAX Counter32
MAX-ACCESS read-only
STATUS current
DESCRIPTION
"This is a status variable.
It is written by the SME when a measurement report is completed.
If dot11STAStatisticsMeasurementDuration is 0, this attribute indicates
the value of dot11RSNAStatsRobustMgmtCCMPReplays returned from the STA in
this STA Statistics Report. If dot11STAStatisticsMeasurementDuration indicates
a nonzero value, this attribute indicates the difference in the referenced
dot11 variable over the indicated duration. This attribute is only
valid if the dot11STAStatisticsGroupID is 16, and is ignored otherwise."
::= { dot11STAStatisticsReportEntry 44 }
dot11STAStatisticsRSNAStatsTKIPICVErrors OBJECT-TYPE
SYNTAX Counter32
MAX-ACCESS read-only
STATUS current
DESCRIPTION
"This is a status variable.
It is written by the SME when a measurement report is completed.
If dot11STAStatisticsMeasurementDuration is 0, this attribute indicates
the value of dot11RSNAStatsTKIPICVErrors returned from the STA in this STA
Statistics Report. If dot11STAStatisticsMeasurementDuration indicates a
nonzero value, this attribute indicates the difference in the referenced
dot11 variable over the indicated duration. This attribute is only valid
if the dot11STAStatisticsGroupID is 16, and is ignored otherwise."
::= { dot11STAStatisticsReportEntry 45 }
dot11STAStatisticsRSNAStatsTKIPReplays OBJECT-TYPE
SYNTAX Counter32
MAX-ACCESS read-only
STATUS current
DESCRIPTION
"This is a status variable.
It is written by the SME when a measurement report is completed.
If dot11STAStatisticsMeasurementDuration is 0, this attribute indicates
the value of dot11RSNAStatsTKIPReplays returned from the STA in this STA
Statistics Report. If dot11STAStatisticsMeasurementDuration indicates a
nonzero value, this attribute indicates the difference in the referenced
dot11 variable over the indicated duration. This attribute is only valid
if the dot11STAStatisticsGroupID is 16, and is ignored otherwise."
::= { dot11STAStatisticsReportEntry 46 }
dot11STAStatisticsRSNAStatsCCMPDecryptErrors OBJECT-TYPE
SYNTAX Counter32
MAX-ACCESS read-only
STATUS current
DESCRIPTION
"This is a status variable.
It is written by the SME when a measurement report is completed.
If dot11STAStatisticsMeasurementDuration is 0, this attribute indicates
the value of dot11RSNAStatsCCMPDecryptErrors returned from the STA in this
STA Statistics Report. If dot11STAStatisticsMeasurementDuration indicates
a nonzero value, this attribute indicates the difference in the referenced
dot11 variable over the indicated duration. This attribute is only valid
if the dot11STAStatisticsGroupID is 16, and is ignored otherwise."
::= { dot11STAStatisticsReportEntry 47 }
dot11STAStatisticsRSNAStatsCCMPReplays OBJECT-TYPE
SYNTAX Counter32
MAX-ACCESS read-only
STATUS current
DESCRIPTION
"This is a status variable.
It is written by the SME when a measurement report is completed.
If dot11STAStatisticsMeasurementDuration is 0, this attribute indicates
the value of dot11RSNAStatsCCMPReplays returned from the STA in this STA
Statistics Report. If dot11STAStatisticsMeasurementDuration indicates a
nonzero value, this attribute indicates the difference in the referenced
dot11 variable over the indicated duration. This attribute is only valid
if the dot11STAStatisticsGroupID is 16, and is ignored otherwise."
::= { dot11STAStatisticsReportEntry 48 }
dot11STAStatisticsReportingReasonSTACounters OBJECT-TYPE
SYNTAX OCTET STRING (SIZE(0..1))
MAX-ACCESS read-only
STATUS current
DESCRIPTION
"This is a status variable.
It is written by the SME when a measurement report is completed.
This attribute indicates the trigger reason(s) for this Statistics Report.
Each bit indicates a different trigger condition. When the bit is set to
1, it indicates that the listed trigger threshold has been exceeded:
B0 (least significant bit): dot11Failed,
B1: dotFCSError,
B2: dot11MultipleRetry,
B3: dot11FrameDuplicate,
B4: dot11RTSFailure,
B5: dot11ACKFailure,
B6: dot11Retry,
B7: Reserved.
This attribute is only valid if the dot11STAStatisticsGroupID is 0, and is
ignored otherwise."
::= { dot11STAStatisticsReportEntry 49 }
dot11STAStatisticsReportingReasonQosCounters OBJECT-TYPE
SYNTAX OCTET STRING (SIZE(0..1))
MAX-ACCESS read-only
STATUS current
DESCRIPTION
"This is a status variable.
It is written by the SME when a measurement report is completed.
This attribute indicates the trigger reason(s) for this Statistics Report.
Each bit indicates a different trigger condition. When the bit is set to
1, it indicates that the listed trigger threshold has been exceeded:
B0 (least significant bit): dot11QoSFailed,
B1: dotQoSRetry,
B2: dot11QoSMultipleRetry,
B3: dot11QoSFrameDuplicate,
B4: dot11QoSRTSFailure,
B5: dot11QoSACKFailure,
B6: dot11QoSDiscarded,
B7: Reserved.
This attribute is only valid if the dot11STAStatisticsGroupID is 2-9, and
is ignored otherwise."
::= { dot11STAStatisticsReportEntry 50 }
dot11STAStatisticsReportingReasonRsnaCounters OBJECT-TYPE
SYNTAX OCTET STRING (SIZE(0..1))
MAX-ACCESS read-only
STATUS current
DESCRIPTION
"This is a status variable.
It is written by the SME when a measurement report is completed.
This attribute indicates the trigger reason(s) for this Statistics Report.
Each bit indicates a different trigger condition. When the bit is set to
1, it indicates that the listed trigger threshold has been exceeded:
B0 (least significant bit): dot11RSNAStatsCMACICVErrors,
B1: dotRSNAStatsCMACReplays,
B2: dot11RSNAStatsRobustMgmtCCMPReplays,
B3: dot11RSNAStatsTKIPICVErrors,
B4: dot11RSNAStatsCCMPReplays,
B5: dot11RSNAStatsCCMPDecryptErrors,
B6: dot11RSNAStatsCCMPReplays,
B7: Reserved.
This attribute is only valid if the dot11STAStatisticsGroupID is 16, and
is ignored otherwise."
::= { dot11STAStatisticsReportEntry 51 }
dot11STAStatisticsTransmittedAMSDUCount OBJECT-TYPE
SYNTAX Counter32
MAX-ACCESS read-only
STATUS current
DESCRIPTION
"This is a status variable.
It is written by the SME when a measurement report is completed.
If dot11STAStatisticsMeasurementDuration is zero, this attribute indicates
the value of dot11TransmittedAMSDUCount returned from the STA in this STA
Statistics Report. If dot11STAStatisticsMeasurementDuration indicates a
nonzero value, this attribute indicates the difference in the referenced
dot11 variable over the indicated duration. This attribute is only valid
if the dot11STAStatisticsGroupID is 11, and is ignored otherwise."
::= { dot11STAStatisticsReportEntry 52 }
dot11STAStatisticsFailedAMSDUCount OBJECT-TYPE
SYNTAX Counter32
MAX-ACCESS read-only
STATUS current
DESCRIPTION
"This is a status variable.
It is written by the SME when a measurement report is completed.
If dot11STAStatisticsMeasurementDuration is zero, this attribute indicates
the value of dot11FailedAMSDUCount returned from the STA in this STA Statistics
Report. If dot11STAStatisticsMeasurementDuration indicates a nonzero
value, this attribute indicates the difference in the referenced
dot11 variable over the indicated duration. This attribute is only valid
if the dot11STAStatisticsGroupID is 11, and is ignored otherwise."
::= { dot11STAStatisticsReportEntry 53 }
dot11STAStatisticsRetryAMSDUCount OBJECT-TYPE
SYNTAX Counter32
MAX-ACCESS read-only
STATUS current
DESCRIPTION
"This is a status variable.
It is written by the SME when a measurement report is completed.
If dot11STAStatisticsMeasurementDuration is zero, this attribute indicates
the value of dot11RetryAMSDUCount returned from the STA in this STA Statistics
Report. If dot11STAStatisticsMeasurementDuration indicates a nonzero
value, this attribute indicates the difference in the referenced
dot11 variable over the indicated duration. This attribute is only valid
if the dot11STAStatisticsGroupID is 11, and is ignored otherwise."
::= { dot11STAStatisticsReportEntry 54 }
dot11STAStatisticsMultipleRetryAMSDUCount OBJECT-TYPE
SYNTAX Counter32
MAX-ACCESS read-only
STATUS current
DESCRIPTION
"This is a status variable.
It is written by the SME when a measurement report is completed.
If dot11STAStatisticsMeasurementDuration is zero, this attribute indicates
the value of dot11MultipleRetryAMSDUCount returned from the STA in this
STA Statistics Report. If dot11STAStatisticsMeasurementDuration indicates
a nonzero value, this attribute indicates the difference in the referenced
dot11 variable over the indicated duration. This attribute is only valid
if the dot11STAStatisticsGroupID is 11, and is ignored otherwise."
::= { dot11STAStatisticsReportEntry 55 }
dot11STAStatisticsTransmittedOctetsInAMSDUCount OBJECT-TYPE
SYNTAX Counter64
MAX-ACCESS read-only
STATUS current
DESCRIPTION
"This is a status variable.
It is written by the SME when a measurement report is completed.
If dot11STAStatisticsMeasurementDuration is zero, this attribute indicates
the value of dot11TransmittedOctetsInAMSDUCount returned from the STA in
this STA Statistics Report. If dot11STAStatisticsMeasurementDuration indicates
a nonzero value, this attribute indicates the difference in the referenced
dot11 variable over the indicated duration. This attribute is only
valid if the dot11STAStatisticsGroupID is 11, and is ignored otherwise."
::= { dot11STAStatisticsReportEntry 56 }
dot11STAStatisticsAMSDUAckFailureCount OBJECT-TYPE
SYNTAX Counter32
MAX-ACCESS read-only
STATUS current
DESCRIPTION
"This is a status variable.
It is written by the SME when a measurement report is completed.
If dot11STAStatisticsMeasurementDuration is zero, this attribute indicates
the value of dot11AMSDUAckFailureCount returned from the STA in this STA
Statistics Report. If dot11STAStatisticsMeasurementDuration indicates a
nonzero value, this attribute indicates the difference in the referenced
dot11 variable over the indicated duration. This attribute is only valid
if the dot11STAStatisticsGroupID is 11, and is ignored otherwise."
::= { dot11STAStatisticsReportEntry 57 }
dot11STAStatisticsReceivedAMSDUCount OBJECT-TYPE
SYNTAX Counter32
MAX-ACCESS read-only
STATUS current
DESCRIPTION
"This is a status variable.
It is written by the SME when a measurement report is completed.
If dot11STAStatisticsMeasurementDuration is zero, this attribute indicates
the value of dot11ReceivedAMSDUCount returned from the STA in this STA
Statistics Report. If dot11STAStatisticsMeasurementDuration indicates a
nonzero value, this attribute indicates the difference in the referenced
dot11 variable over the indicated duration. This attribute is only valid
if the dot11STAStatisticsGroupID is 11, and is ignored otherwise."
::= { dot11STAStatisticsReportEntry 58 }
dot11STAStatisticsReceivedOctetsInAMSDUCount OBJECT-TYPE
SYNTAX Counter64
MAX-ACCESS read-only
STATUS current
DESCRIPTION
"This is a status variable.
It is written by the SME when a measurement report is completed.
If dot11STAStatisticsMeasurementDuration is zero, this attribute indicates
the value of dot11ReceivedOctetsInAMSDUCount returned from the STA in this
STA Statistics Report. If dot11STAStatisticsMeasurementDuration indicates
a nonzero value, this attribute indicates the difference in the referenced
dot11 variable over the indicated duration. This attribute is onl/y valid
if the dot11STAStatisticsGroupID is 11, and is ignored otherwise."
::= { dot11STAStatisticsReportEntry 59 }
dot11STAStatisticsTransmittedAMPDUCount OBJECT-TYPE
SYNTAX Counter32
MAX-ACCESS read-only
STATUS current
DESCRIPTION
"This is a status variable.
It is written by the SME when a measurement report is completed.
If dot11STAStatisticsMeasurementDuration is zero, this attribute indicates
the value of dot11TransmittedAMPDUCount returned from the STA in this STA
Statistics Report. If dot11STAStatisticsMeasurementDuration indicates a
nonzero value, this attribute indicates the difference in the referenced
dot11 variable over the indicated duration. This attribute is only valid
if the dot11STAStatisticsGroupID is 12, and is ignored otherwise."
::= { dot11STAStatisticsReportEntry 60 }
dot11STAStatisticsTransmittedMPDUsInAMPDUCount OBJECT-TYPE
SYNTAX Counter32
MAX-ACCESS read-only
STATUS current
DESCRIPTION
"This is a status variable.
It is written by the SME when a measurement report is completed.
If dot11STAStatisticsMeasurementDuration is zero, this attribute indicates
the value of dot11TransmittedMPDUsInAMPDUCount returned from the STA in
this STA Statistics Report. If dot11STAStatisticsMeasurementDuration indicates
a nonzero value, this attribute indicates the difference in the referenced
dot11 variable over the indicated duration. This attribute is only
valid if the dot11STAStatisticsGroupID is 12, and is ignored otherwise."
::= { dot11STAStatisticsReportEntry 61 }
dot11STAStatisticsTransmittedOctetsInAMPDUCount OBJECT-TYPE
SYNTAX Counter64
MAX-ACCESS read-only
STATUS current
DESCRIPTION
"This is a status variable.
It is written by the SME when a measurement report is completed.
If dot11STAStatisticsMeasurementDuration is zero, this attribute indicates
the value of dot11TransmittedOctetsInAMPDUCount returned from the STA in
this STA Statistics Report. If dot11STAStatisticsMeasurementDuration indicates
a nonzero value, this attribute indicates the difference in the referenced
dot11 variable over the indicated duration. This attribute is only
valid if the dot11STAStatisticsGroupID is 12, and is ignored otherwise."
::= { dot11STAStatisticsReportEntry 62 }
dot11STAStatisticsAMPDUReceivedCount OBJECT-TYPE
SYNTAX Counter32
MAX-ACCESS read-only
STATUS current
DESCRIPTION
"This is a status variable.
It is written by the SME when a measurement report is completed.
If dot11STAStatisticsMeasurementDuration is zero, this attribute indicates
the value of dot11AMPDUReceivedCount returned from the STA in this STA
Statistics Report. If dot11STAStatisticsMeasurementDuration indicates a
nonzero value, this attribute indicates the difference in the referenced
dot11 variable over the indicated duration. This attribute is only valid
if the dot11STAStatisticsGroupID is 12, and is ignored otherwise."
::= { dot11STAStatisticsReportEntry 63 }
dot11STAStatisticsMPDUInReceivedAMPDUCount OBJECT-TYPE
SYNTAX Counter32
MAX-ACCESS read-only
STATUS current
DESCRIPTION
"This is a status variable.
It is written by the SME when a measurement report is completed.
If dot11STAStatisticsMeasurementDuration is zero, this attribute indicates
the value of dot11MPDUInReceivedAMPDUCount returned from the STA in this
STA Statistics Report. If dot11STAStatisticsMeasurementDuration indicates
a nonzero value, this attribute indicates the difference in the referenced
dot11 variable over the indicated duration. This attribute is only valid
if the dot11STAStatisticsGroupID is 12, and is ignored otherwise."
::= { dot11STAStatisticsReportEntry 64 }
dot11STAStatisticsReceivedOctetsInAMPDUCount OBJECT-TYPE
SYNTAX Counter64
MAX-ACCESS read-only
STATUS current
DESCRIPTION
"This is a status variable.
It is written by the SME when a measurement report is completed.
If dot11STAStatisticsMeasurementDuration is zero, this attribute indicates
the value of dot11ReceivedOctetsInAMPDUCount returned from the STA in this
STA Statistics Report. If dot11STAStatisticsMeasurementDuration indicates
a nonzero value, this attribute indicates the difference in the referenced
dot11 variable over the indicated duration. This attribute is only valid
if the dot11STAStatisticsGroupID is 12, and is ignored otherwise."
::= { dot11STAStatisticsReportEntry 65 }
dot11STAStatisticsAMPDUDelimiterCRCErrorCount OBJECT-TYPE
SYNTAX Counter32
MAX-ACCESS read-only
STATUS current
DESCRIPTION
"This is a status variable.
It is written by the SME when a measurement report is completed.
If dot11STAStatisticsMeasurementDuration is zero, this attribute indicates
the value of dot11AMPDUDelimiterCRCErrorCount returned from the STA in
this STA Statistics Report. If dot11STAStatisticsMeasurementDuration indicates
a nonzero value, this attribute indicates the difference in the referenced
dot11 variable over the indicated duration. This attribute is only
valid if the dot11STAStatisticsGroupID is 12, and is ignored otherwise."
::= { dot11STAStatisticsReportEntry 66 }
dot11STAStatisticsImplicitBARFailureCount OBJECT-TYPE
SYNTAX Counter32
MAX-ACCESS read-only
STATUS current
DESCRIPTION
"This is a status variable.
It is written by the SME when a measurement report is completed.
If dot11STAStatisticsMeasurementDuration is zero, this attribute indicates
the value of dot11ImplicitBARFailureCount returned from the STA in this
STA Statistics Report. If dot11STAStatisticsMeasurementDuration indicates
a nonzero value, this attribute indicates the difference in the referenced
dot11 variable over the indicated duration. This attribute is only valid
if the dot11STAStatisticsGroupID is 13, and is ignored otherwise."
::= { dot11STAStatisticsReportEntry 67 }
dot11STAStatisticsExplicitBARFailureCount OBJECT-TYPE
SYNTAX Counter32
MAX-ACCESS read-only
STATUS current
DESCRIPTION
"This is a status variable.
It is written by the SME when a measurement report is completed.
If dot11STAStatisticsMeasurementDuration is zero, this attribute indicates
the value of dot11ExplicitBARFailureCount returned from the STA in this
STA Statistics Report. If dot11STAStatisticsMeasurementDuration indicates
a nonzero value, this attribute indicates the difference in the referenced
dot11 variable over the indicated duration. This attribute is only valid
if the dot11STAStatisticsGroupID is 13, and is ignored otherwise."
::= { dot11STAStatisticsReportEntry 68 }
dot11STAStatisticsChannelWidthSwitchCount OBJECT-TYPE
SYNTAX Counter32
MAX-ACCESS read-only
STATUS current
DESCRIPTION
"This is a status variable.
It is written by the SME when a measurement report is completed.
If dot11STAStatisticsMeasurementDuration is zero, this attribute indicates
the value of dot11ChannelWidthSwitchCount returned from the STA in this
STA Statistics Report. If dot11STAStatisticsMeasurementDuration indicates
a nonzero value, this attribute indicates the difference in the referenced
dot11 variable over the indicated duration. This attribute is only valid
if the dot11STAStatisticsGroupID is 13, and is ignored otherwise."
::= { dot11STAStatisticsReportEntry 69 }
dot11STAStatisticsTwentyMHzFrameTransmittedCount OBJECT-TYPE
SYNTAX Counter32
MAX-ACCESS read-only
STATUS current
DESCRIPTION
"This is a status variable.
It is written by the SME when a measurement report is completed.
If dot11STAStatisticsMeasurementDuration is zero, this attribute indicates
the value of dot11TwentyMHzFrameTransmittedCount returned from the STA in
this STA Statistics Report. If dot11STAStatisticsMeasurementDuration indicates
a nonzero value, this attribute indicates the difference in the referenced
dot11 variable over the indicated duration. This attribute is only
valid if the dot11STAStatisticsGroupID is 13, and is ignored otherwise."
::= { dot11STAStatisticsReportEntry 70 }
dot11STAStatisticsFortyMHzFrameTransmittedCount OBJECT-TYPE
SYNTAX Counter32
MAX-ACCESS read-only
STATUS current
DESCRIPTION
"This is a status variable.
It is written by the SME when a measurement report is completed.
If dot11STAStatisticsMeasurementDuration is zero, this attribute indicates
the value of dot11FortyMHzFrameTransmittedCount returned from the STA in
this STA Statistics Report. If dot11STAStatisticsMeasurementDuration indicates
a nonzero value, this attribute indicates the difference in the referenced
dot11 variable over the indicated duration. This attribute is only
valid if the dot11STAStatisticsGroupID is 13, and is ignored otherwise."
::= { dot11STAStatisticsReportEntry 71 }
dot11STAStatisticsTwentyMHzFrameReceivedCount OBJECT-TYPE
SYNTAX Counter32
MAX-ACCESS read-only
STATUS current
DESCRIPTION
"This is a status variable.
It is written by the SME when a measurement report is completed.
If dot11STAStatisticsMeasurementDuration is zero, this attribute indicates
the value of dot11TwentyMHzFrameReceivedCount returned from the STA in
this STA Statistics Report. If dot11STAStatisticsMeasurementDuration indicates
a nonzero value, this attribute indicates the difference in the referenced
dot11 variable over the indicated duration. This attribute is only
valid if the dot11STAStatisticsGroupID is 13, and is ignored otherwise."
::= { dot11STAStatisticsReportEntry 72 }
dot11STAStatisticsFortyMHzFrameReceivedCount OBJECT-TYPE
SYNTAX Counter32
MAX-ACCESS read-only
STATUS current
DESCRIPTION
"This is a status variable.
It is written by the SME when a measurement report is completed.
If dot11STAStatisticsMeasurementDuration is zero, this attribute indicates
the value of dot11FortyMHzFrameReceivedCount returned from the STA in this
STA Statistics Report. If dot11STAStatisticsMeasurementDuration indicates
a nonzero value, this attribute indicates the difference in the referenced
dot11 variable over the indicated duration. This attribute is only valid
if the dot11STAStatisticsGroupID is 13, and is ignored otherwise."
::= { dot11STAStatisticsReportEntry 73 }
dot11STAStatisticsPSMPUTTGrantDuration OBJECT-TYPE
SYNTAX Counter32
MAX-ACCESS read-only
STATUS current
DESCRIPTION
"This is a status variable.
It is written by the SME when a measurement report is completed.
If dot11STAStatisticsMeasurementDuration is zero, this attribute indicates
the value of dot11PSMPUTTGrantDuration returned from the STA in this STA
Statistics Report. If dot11STAStatisticsMeasurementDuration indicates a
nonzero value, this attribute indicates the difference in the referenced
dot11 variable over the indicated duration. This attribute is only valid
if the dot11STAStatisticsGroupID is 13, and is ignored otherwise."
::= { dot11STAStatisticsReportEntry 74 }
dot11STAStatisticsPSMPUTTUsedDuration OBJECT-TYPE
SYNTAX Counter32
MAX-ACCESS read-only
STATUS current
DESCRIPTION
"This is a status variable.
It is written by the SME when a measurement report is completed.
If dot11STAStatisticsMeasurementDuration is zero, this attribute indicates
the value of dot11PSMPUTTUsedDuration returned from the STA in this STA
Statistics Report. If dot11STAStatisticsMeasurementDuration indicates a
nonzero value, this attribute indicates the difference in the referenced
dot11 variable over the indicated duration. This attribute is only valid
if the dot11STAStatisticsGroupID is 13, and is ignored otherwise."
::= { dot11STAStatisticsReportEntry 75 }
dot11STAStatisticsGrantedRDGUsedCount OBJECT-TYPE
SYNTAX Counter32
MAX-ACCESS read-only
STATUS current
DESCRIPTION
"This is a status variable.
It is written by the SME when a measurement report is completed.
If dot11STAStatisticsMeasurementDuration is zero, this attribute indicates
the value of dot11GrantedRDGUsedCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 76 }
dot11STAStatisticsGrantedRDGUnusedCount OBJECT-TYPE
SYNTAX Counter32
MAX-ACCESS read-only
STATUS current
DESCRIPTION
"This is a status variable.
It is written by the SME when a measurement report is completed.
If dot11STAStatisticsMeasurementDuration is zero, this attribute indicates
the value of dot11GrantedRDGUnusedCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 77 }
dot11STAStatisticsTransmittedFramesInGrantedRDGCount OBJECT-TYPE
SYNTAX Counter32
MAX-ACCESS read-only
STATUS current
DESCRIPTION
"This is a status variable.
It is written by the SME when a measurement report is completed.
If dot11STAStatisticsMeasurementDuration is zero, this attribute indicates
the value of dot11TransmittedFramesInGrantedRDGCount returned from the STA
in this STA Statistics Report. If dot11STAStatisticsMeasurementDuration
indicates a nonzero value, this attribute indicates the difference in the
referenced dot11 variable over the indicated duration. This attribute is
only valid if the dot11STAStatisticsGroupID is 14, and is ignored otherwise."
::= { dot11STAStatisticsReportEntry 78 }
dot11STAStatisticsTransmittedOctetsInGrantedRDGCount OBJECT-TYPE
SYNTAX Counter64
MAX-ACCESS read-only
STATUS current
DESCRIPTION
"This is a status variable.
It is written by the SME when a measurement report is completed.
If dot11STAStatisticsMeasurementDuration is zero, this attribute indicates
the value of dot11TransmittedOctetsInGrantedRDGCount returned from the STA
in this STA Statistics Report. If dot11STAStatisticsMeasurementDuration
indicates a nonzero value, this attribute indicates the difference in the
referenced dot11 variable over the indicated duration. This attribute is
only valid if the dot11STAStatisticsGroupID is 14, and is ignored otherwise."
::= { dot11STAStatisticsReportEntry 79 }
dot11STAStatisticsDualCTSSuccessCount OBJECT-TYPE
SYNTAX Counter32
MAX-ACCESS read-only
STATUS current
DESCRIPTION
"This is a status variable.
It is written by the SME when a measurement report is completed.
If dot11STAStatisticsMeasurementDuration is zero, this attribute indicates
the value of dot11DualCTSSuccessCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 80 }
dot11STAStatisticsDualCTSFailureCount OBJECT-TYPE
SYNTAX Counter32
MAX-ACCESS read-only
STATUS current
DESCRIPTION
"This is a status variable.
It is written by the SME when a measurement report is completed.
If dot11STAStatisticsMeasurementDuration is zero, this attribute indicates
the value of dot11DualCTSFailureCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 81 }
dot11STAStatisticsRTSLSIGSuccessCount OBJECT-TYPE
SYNTAX Counter32
MAX-ACCESS read-only
STATUS current
DESCRIPTION
"This is a status variable.
It is written by the SME when a measurement report is completed.
If dot11STAStatisticsMeasurementDuration is zero, this attribute indicates
the value of dot11RTSLSIGSuccessCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 82 }
dot11STAStatisticsRTSLSIGFailureCount OBJECT-TYPE
SYNTAX Counter32
MAX-ACCESS read-only
STATUS current
DESCRIPTION
"This is a status variable.
It is written by the SME when a measurement report is completed.
If dot11STAStatisticsMeasurementDuration is zero, this attribute indicates
the value of dot11RTSLSIGFailureCount returned from the STA in this STA
Statistics Report. If dot11STAStatisticsMeasurementDuration indicates a
nonzero value, this attribute indicates the difference in the referenced
dot11 variable over the indicated duration. This attribute is only valid
if the dot11STAStatisticsGroupID is 14, and is ignored otherwise."
::= { dot11STAStatisticsReportEntry 83 }
dot11STAStatisticsBeamformingFrameCount OBJECT-TYPE
SYNTAX Counter32
MAX-ACCESS read-only
STATUS current
DESCRIPTION
"This is a status variable.
It is written by the SME when a measurement report is completed.
If dot11STAStatisticsMeasurementDuration is zero, this attribute indicates
the value of dot11BeamformingFrameCount returned from the STA in this STA
Statistics Report. If dot11STAStatisticsMeasurementDuration indicates a
nonzero value, this attribute indicates the difference in the referenced
dot11 variable over the indicated duration. This attribute is only valid
if the dot11STAStatisticsGroupID is 15, and is ignored otherwise."
::= { dot11STAStatisticsReportEntry 84 }
dot11STAStatisticsSTBCCTSSuccessCount OBJECT-TYPE
SYNTAX Counter32
MAX-ACCESS read-only
STATUS current
DESCRIPTION
"This is a status variable.
It is written by the SME when a measurement report is completed.
If dot11STAStatisticsMeasurementDuration is zero, this attribute indicates
the value of dot11STBCCTSSuccessCount returned from the STA in this STA
Statistics Report. If dot11STAStatisticsMeasurementDuration indicates a
nonzero value, this attribute indicates the difference in the referenced
dot11 variable over the indicated duration. This attribute is only valid
if the dot11STAStatisticsGroupID is 15, and is ignored otherwise."
::= { dot11STAStatisticsReportEntry 85 }
dot11STAStatisticsSTBCCTSFailureCount OBJECT-TYPE
SYNTAX Counter32
MAX-ACCESS read-only
STATUS current
DESCRIPTION
"This is a status variable.
It is written by the SME when a measurement report is completed.
If dot11STAStatisticsMeasurementDuration is zero, this attribute indicates
the value of dot11STBCCTSFailureCount returned from the STA in this STA
Statistics Report. If dot11STAStatisticsMeasurementDuration indicates a
nonzero value, this attribute indicates the difference in the referenced
dot11 variable over the indicated duration. This attribute is only valid
if the dot11STAStatisticsGroupID is 15, and is ignored otherwise."
::= { dot11STAStatisticsReportEntry 86 }
dot11STAStatisticsnonSTBCCTSSuccessCount OBJECT-TYPE
SYNTAX Counter32
MAX-ACCESS read-only
STATUS current
DESCRIPTION
"This is a status variable.
It is written by the SME when a measurement report is completed.
If dot11STAStatisticsMeasurementDuration is zero, this attribute indicates
the value of dot11nonSTBCCTSSuccessCountt returned from the STA in this
STA Statistics Report. If dot11STAStatisticsMeasurementDuration indicates
a nonzero value, this attribute indicates the difference in the referenced
dot11 variable over the indicated duration. This attribute is only valid
if the dot11STAStatisticsGroupID is 15, and is ignored otherwise."
::= { dot11STAStatisticsReportEntry 87 }
dot11STAStatisticsnonSTBCCTSFailureCount OBJECT-TYPE
SYNTAX Counter32
MAX-ACCESS read-only
STATUS current
DESCRIPTION
"This is a status variable.
It is written by the SME when a measurement report is completed.
If dot11STAStatisticsMeasurementDuration is zero, this attribute indicates
the value of dot11nonSTBCCTSFailureCount returned from the STA in this STA
Statistics Report. If dot11STAStatisticsMeasurementDuration indicates a
nonzero value, this attribute indicates the difference in the referenced
dot11 variable over the indicated duration. This attribute is only valid
if the dot11STAStatisticsGroupID is 15, and is ignored otherwise."
::= { dot11STAStatisticsReportEntry 88 }
-- ********************************************************************
-- * End of dot11STAStatisticsReport TABLE
-- ********************************************************************
-- ********************************************************************
-- * dot11LCIReport TABLE
-- ********************************************************************
dot11LCIReportTable OBJECT-TYPE
SYNTAX SEQUENCE OF Dot11LCIReportEntry
MAX-ACCESS not-accessible
STATUS current
DESCRIPTION
"This table contains the current list of LCI reports that have been received
by the MLME. The report tables are maintained as a FIFO to preserve freshness,
thus the rows in this table can be deleted for memory constraints or
other implementation constraints determined by the vendor. New rows have
different RprtIndex values than those deleted within the range limitation
of the index. One easy way is to monotonically increase RprtIndex for new
reports being written in the table."
::= { dot11RMReport 6 }
dot11LCIReportEntry OBJECT-TYPE
SYNTAX Dot11LCIReportEntry
MAX-ACCESS not-accessible
STATUS current
DESCRIPTION
"An entry in the dot11LCIReportTable Indexed by dot11LCIReportIndex."
INDEX { dot11LCIReportIndex }
::= { dot11LCIReportTable 1 }
Dot11LCIReportEntry ::=
SEQUENCE {
dot11LCIReportIndex Unsigned32,
dot11LCIReportToken OCTET STRING,
dot11LCIIfIndex InterfaceIndex,
dot11LCISTAAddress MacAddress,
dot11LCILatitudeResolution Unsigned32,
dot11LCILatitudeInteger Integer32,
dot11LCILatitudeFraction Integer32,
dot11LCILongitudeResolution Unsigned32,
dot11LCILongitudeInteger Integer32,
dot11LCILongitudeFraction Integer32,
dot11LCIAltitudeType INTEGER,
dot11LCIAltitudeResolution Unsigned32,
dot11LCIAltitudeInteger Integer32,
dot11LCIAltitudeFraction Integer32,
dot11LCIDatum Unsigned32,
dot11LCIAzimuthType INTEGER,
dot11LCIAzimuthResolution Unsigned32,
dot11LCIAzimuth Integer32,
dot11LCIVendorSpecific OCTET STRING,
dot11LCIRprtMeasurementMode INTEGER}
dot11LCIReportIndex OBJECT-TYPE
SYNTAX Unsigned32
MAX-ACCESS not-accessible
STATUS current
DESCRIPTION
"Index for LCI Report elements in dot11LCIReportTable, greater than 0."
::= { dot11LCIReportEntry 1 }
dot11LCIReportToken OBJECT-TYPE
SYNTAX OCTET STRING
MAX-ACCESS read-only
STATUS current
DESCRIPTION
"This is a status variable.
It is written by the SME when a measurement report is completed.
This attribute indicates the token that was indicated in the measurement
request that generated this measurement report. This should be an exact
match to the original dot11RMRqstToken attribute. Note that there may be
multiple entries in the table that match this value since a single request
may generate multiple measurement reports."
::= { dot11LCIReportEntry 2 }
dot11LCIIfIndex OBJECT-TYPE
SYNTAX InterfaceIndex
MAX-ACCESS read-only
STATUS current
DESCRIPTION
"This is a status variable.
It is written by the SME when a measurement report is completed.
Identifies the Interface that this row of LCI Report has been received on"
::= { dot11LCIReportEntry 3 }
dot11LCISTAAddress OBJECT-TYPE
SYNTAX MacAddress
MAX-ACCESS read-only
STATUS current
DESCRIPTION
"This is a status variable.
It is written by the SME when a measurement report is completed.
The MAC address of the STA that returned this LCI Report."
::= { dot11LCIReportEntry 4 }
dot11LCILatitudeResolution OBJECT-TYPE
SYNTAX Unsigned32 (0..63)
MAX-ACCESS read-only
STATUS current
DESCRIPTION
"This is a status variable.
It is written by the SME when a measurement report is completed.
This attribute indicates the latitude resolution as 6 bits indicating the
number of valid bits in the fixed-point value of Latitude. This field is
derived from IETF RFC 3825."
::= { dot11LCIReportEntry 5 }
dot11LCILatitudeInteger OBJECT-TYPE
SYNTAX Integer32 (-359..359)
MAX-ACCESS read-only
STATUS current
DESCRIPTION
"This is a status variable.
It is written by the SME when a measurement report is completed.
This attribute indicates the latitude as a 34 bit fixed point value consisting
of 9 bits of integer and 25 bits of fraction. This field contains
the 9 bits of integer portion of Latitude. This field is derived from IETF
RFC 3825."
::= { dot11LCIReportEntry 6 }
dot11LCILatitudeFraction OBJECT-TYPE
SYNTAX Integer32 (-16777215..16777215)
MAX-ACCESS read-only
STATUS current
DESCRIPTION
"This is a status variable.
It is written by the SME when a measurement report is completed.
This attribute indicates the latitude as a 34 bit fixed point value consisting
of 9 bits of integer and 25 bits of fraction. This field contains
the 25 bits of fraction portion of Latitude. This field is derived from
IETF RFC 3825."
::= { dot11LCIReportEntry 7 }
dot11LCILongitudeResolution OBJECT-TYPE
SYNTAX Unsigned32 (0..63)
MAX-ACCESS read-only
STATUS current
DESCRIPTION
"This is a status variable.
It is written by the SME when a measurement report is completed.
This attribute indicates the longitude resolution as 6 bits indicating the
number of valid bits in the fixed-point value of Longitude. This field is
derived from IETF RFC 3825."
::= { dot11LCIReportEntry 8 }
dot11LCILongitudeInteger OBJECT-TYPE
SYNTAX Integer32 (-359..359)
MAX-ACCESS read-only
STATUS current
DESCRIPTION
"This is a status variable.
It is written by the SME when a measurement report is completed.
This attribute indicates the longitude as a 34 bit fixed point value consisting
of 9 bits of integer and 25 bits of fraction. This field contains
the 9 bits of integer portion of Longitude. This field is derived from
IETF RFC 3825."
::= { dot11LCIReportEntry 9 }
dot11LCILongitudeFraction OBJECT-TYPE
SYNTAX Integer32 (-16777215..16777215)
MAX-ACCESS read-only
STATUS current
DESCRIPTION
"This is a status variable.
It is written by the SME when a measurement report is completed.
This attribute indicates the longitude as a 34 bit fixed point value consisting
of 9 bits of integer and 25 bits of fraction. This field contains
the 25 bits of fraction portion of Longitude. This field is derived from
IETF RFC 3825."
::= { dot11LCIReportEntry 10 }
dot11LCIAltitudeType OBJECT-TYPE
SYNTAX INTEGER { meters(1), floors(2) }
MAX-ACCESS read-only
STATUS current
DESCRIPTION
"This is a status variable.
It is written by the SME when a measurement report is completed.
This attribute indicates the altitude Type. Codes defined are:
meters : in 2s-complement fixed-point 22-bit integer part with 8-bit fraction
floors : in 2s-complement fixed-point 22-bit integer part with 8-bit fraction.
This field is derived from IETF RFC 3825."
::= { dot11LCIReportEntry 11 }
dot11LCIAltitudeResolution OBJECT-TYPE
SYNTAX Unsigned32 (0..63)
MAX-ACCESS read-only
STATUS current
DESCRIPTION
"This is a status variable.
It is written by the SME when a measurement report is completed.
This attribute indicates the altitude resolution as 6 bits indicating the
number of valid bits in the altitude. This field is derived from IETF RFC
3825."
::= { dot11LCIReportEntry 12 }
dot11LCIAltitudeInteger OBJECT-TYPE
SYNTAX Integer32 (-2097151..2097151)
MAX-ACCESS read-only
STATUS current
DESCRIPTION
"This is a status variable.
It is written by the SME when a measurement report is completed.
This attribute indicates the altitude as a 30 bit value defined by the
Altitude type field. The field is encoded as a 2s-complement fixed-point
22-bit integer Part with 8-bit fraction. This field contains the fixedpoint
Part of Altitude. This field is derived from IETF RFC 3825."
::= { dot11LCIReportEntry 13 }
dot11LCIAltitudeFraction OBJECT-TYPE
SYNTAX Integer32 (-127..127)
MAX-ACCESS read-only
STATUS current
DESCRIPTION
"This is a status variable.
It is written by the SME when a measurement report is completed.
This attribute indicates the altitude as a 30 bit value defined by the
Altitude type field. The field is encoded as a 2s-complement fixed-point
22-bit integer Part with 8-bit fraction. This field contains the fraction
part of Altitude. This field is derived from IETF RFC 3825."
::= { dot11LCIReportEntry 14 }
dot11LCIDatum OBJECT-TYPE
SYNTAX Unsigned32 (0..255)
MAX-ACCESS read-only
STATUS current
DESCRIPTION
"This is a status variable.
It is written by the SME when a measurement report is completed.
This attribute indicates the datum as an eight-bit value encoding the horizontal
and vertical references used for the coordinates given in this
LCI."
::= { dot11LCIReportEntry 15 }
dot11LCIAzimuthType OBJECT-TYPE
SYNTAX INTEGER { frontSurfaceOfSTA(0), radioBeam(1) }
MAX-ACCESS read-only
STATUS current
DESCRIPTION
"This is a status variable.
It is written by the SME when a measurement report is completed.
This attribute indicates the azimuth Type as a one bit attribute encoding
the type of Azimuth. Codes defined are: front surface of STA : in 2s-complement
fixed-point 9-bit integer; and radio beam : in 2s-complement
fixed-point 9-bit integer"
::= { dot11LCIReportEntry 16 }
dot11LCIAzimuthResolution OBJECT-TYPE
SYNTAX Unsigned32 (0..15)
MAX-ACCESS read-only
STATUS current
DESCRIPTION
"This is a status variable.
It is written by the SME when a measurement report is completed.
This attribute indicates the azimuth Resolution as 4 bits indicating the
number of valid bits in the azimuth."
::= { dot11LCIReportEntry 17 }
dot11LCIAzimuth OBJECT-TYPE
SYNTAX Integer32
MAX-ACCESS read-only
STATUS current
DESCRIPTION
"This is a status variable.
It is written by the SME when a measurement report is completed.
This attribute indicates the azimuth as a 9 bit value defined by the Azimuth
Type field.The field is encoded as a 2s-complement fixed-point 9-bit
integer horizontal angle in degrees from true north."
::= { dot11LCIReportEntry 18 }
dot11LCIVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11LCIReportEntry 19 }
dot11LCIRprtMeasurementMode OBJECT-TYPE
SYNTAX INTEGER {
success(0),
incapableBit(1),
refusedBit(2) }
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11LCIReportEntry 20 }
-- ********************************************************************
-- * End of dot11LCIReport TABLE
-- ********************************************************************
-- ********************************************************************
-- * dot11TransmitStreamReport TABLE
-- ********************************************************************
dot11TransmitStreamReportTable OBJECT-TYPE
SYNTAX SEQUENCE OF Dot11TransmitStreamReportEntry
MAX-ACCESS not-accessible
STATUS current
DESCRIPTION
"This table contains the current list of Transmit Delay Metrics reports
that have been received by the MLME. The report tables are maintained as a
FIFO to preserve freshness, thus the rows in this table can be deleted for
memory constraints or other implementation constraints determined by the
vendor. New rows have different RprtIndex values than those deleted within
the range limitation of the index. One easy way is to monotonically
increase RprtIndex for new reports being written in the table."
::= { dot11RMReport 7 }
dot11TransmitStreamReportEntry OBJECT-TYPE
SYNTAX Dot11TransmitStreamReportEntry
MAX-ACCESS not-accessible
STATUS current
DESCRIPTION
"An entry in the dot11TransmitStreamReportTable Indexed by
dot11TransmitStreamRprtIndex."
INDEX { dot11TransmitStreamRprtIndex }
::= { dot11TransmitStreamReportTable 1 }
Dot11TransmitStreamReportEntry ::=
SEQUENCE {
dot11TransmitStreamRprtIndex Unsigned32,
dot11TransmitStreamRprtRqstToken OCTET STRING,
dot11TransmitStreamRprtIfIndex InterfaceIndex,
dot11TransmitStreamMeasuringSTAAddr MacAddress,
dot11TransmitStreamRprtActualStartTime TSFType,
dot11TransmitStreamRprtMeasurementDuration Unsigned32,
dot11TransmitStreamRprtPeerSTAAddress MacAddress,
dot11TransmitStreamRprtTID Unsigned32,
dot11TransmitStreamRprtAverageQueueDelay Unsigned32,
dot11TransmitStreamRprtAverageTransmitDelay Unsigned32,
dot11TransmitStreamRprtTransmittedMSDUCount Unsigned32,
dot11TransmitStreamRprtMSDUDiscardedCount Unsigned32,
dot11TransmitStreamRprtMSDUFailedCount Unsigned32,
dot11TransmitStreamRprtMultipleRetryCount Unsigned32,
dot11TransmitStreamRprtCFPollsLostCount Unsigned32,
dot11TransmitStreamRprtBin0Range Unsigned32,
dot11TransmitStreamRprtDelayHistogram OCTET STRING,
dot11TransmitStreamRprtReason INTEGER,
dot11TransmitStreamRprtVendorSpecific OCTET STRING,
dot11TransmitStreamRprtMeasurementMode INTEGER}
dot11TransmitStreamRprtIndex OBJECT-TYPE
SYNTAX Unsigned32
MAX-ACCESS not-accessible
STATUS current
DESCRIPTION
"Index for Transmit Delay Metrics Report elements in
dot11TransmitStreamReportTable, greater than 0."
::= { dot11TransmitStreamReportEntry 1 }
dot11TransmitStreamRprtRqstToken OBJECT-TYPE
SYNTAX OCTET STRING
MAX-ACCESS read-only
STATUS current
DESCRIPTION
"This is a status variable.
It is written by the SME when a measurement report is completed.
This attribute indicates the request token that was indicated in the measurement
request that generated this measurement report. This should be an
exact match to the original dot11RMRqstToken attribute. Note that there
may be multiple entries in the table that match this value since a single
request may generate multiple measurement reports."
::= { dot11TransmitStreamReportEntry 2 }
dot11TransmitStreamRprtIfIndex OBJECT-TYPE
SYNTAX InterfaceIndex
MAX-ACCESS read-only
STATUS current
DESCRIPTION
"This is a status variable.
It is written by the SME when a measurement report is completed.
The ifIndex of the interface on which this TransmitStream Report was
received."
::= { dot11TransmitStreamReportEntry 3 }
dot11TransmitStreamMeasuringSTAAddr OBJECT-TYPE
SYNTAX MacAddress
MAX-ACCESS read-only
STATUS current
DESCRIPTION
"This is a status variable.
It is written by the SME when a measurement report is completed.
The MAC address of the measuring STA for this row of Transmit Delay Metrics
report."
::= { dot11TransmitStreamReportEntry 4 }
dot11TransmitStreamRprtActualStartTime OBJECT-TYPE
SYNTAX TSFType
MAX-ACCESS read-only
STATUS current
DESCRIPTION
"This is a status variable.
It is written by the SME when a measurement report is completed.
This attribute indicates the TSF value at the time when the measurement
started or for a triggered Transmit Stream/Category Measurement report the
TSF value at the reporting QoS STA when the trigger condition was met."
::= { dot11TransmitStreamReportEntry 5 }
dot11TransmitStreamRprtMeasurementDuration OBJECT-TYPE
SYNTAX Unsigned32
UNITS "TUs"
MAX-ACCESS read-only
STATUS current
DESCRIPTION
"This is a status variable.
It is written by the SME when a measurement report is completed.
This attribute indicates the duration over which the Transmit Delay Metrics
Report was measured. For a triggered Transmit Stream/Category Measurement
Report, metrics are reported over a number of transmitted MSDUs
rather than a duration, hence Measurement Duration is equal to 0."
::= { dot11TransmitStreamReportEntry 6 }
dot11TransmitStreamRprtPeerSTAAddress OBJECT-TYPE
SYNTAX MacAddress
MAX-ACCESS read-only
STATUS current
DESCRIPTION
"This is a status variable.
It is written by the SME when a measurement report is completed.
The MAC address present in the Address 1 field of the measured data
frames for this row of Transmit Stream/Category Measurement report."
::= { dot11TransmitStreamReportEntry 7 }
dot11TransmitStreamRprtTID OBJECT-TYPE
SYNTAX Unsigned32(0..16)
MAX-ACCESS read-only
STATUS current
DESCRIPTION
"This is a status variable.
It is written by the SME when a measurement report is completed.
This attribute indicates the TC or TS for which traffic is to be measured.
Values 0 to 15 are defined. Values 16-255 are reserved."
::= { dot11TransmitStreamReportEntry 8 }
dot11TransmitStreamRprtAverageQueueDelay OBJECT-TYPE
SYNTAX Unsigned32
UNITS "TUs"
MAX-ACCESS read-only
STATUS current
DESCRIPTION
"This is a status variable.
It is written by the SME when a measurement report is completed.
This attribute indicates the average delay of the frames (MSDUs) that are
passed to the MAC during the measurement duration for the indicated destination
and the indicated Traffic Identifier. Queue Delay is measured from
the time the MSDU is passed to the MAC until the transmission starts and
is expressed in units of TUs."
::= { dot11TransmitStreamReportEntry 9 }
dot11TransmitStreamRprtAverageTransmitDelay OBJECT-TYPE
SYNTAX Unsigned32
UNITS "TUs"
MAX-ACCESS read-only
STATUS current
DESCRIPTION
"This is a status variable.
It is written by the SME when a measurement report is completed.
This attribute indicates the average delay of the frames (MSDUs) that are
successfully transmitted during the measurement duration for the indicated
destination and the indicated Traffic Identifier. Delay is measured from
the time the MSDU is passed to the MAC until ACK is received from the
intermediate destination."
::= { dot11TransmitStreamReportEntry 10}
dot11TransmitStreamRprtTransmittedMSDUCount OBJECT-TYPE
SYNTAX Unsigned32
MAX-ACCESS read-only
STATUS current
DESCRIPTION
"This is a status variable.
It is written by the SME when a measurement report is completed.
This attribute indicates the number of MSDUs to the peer STA for the TC,
or TS given by the Traffic Identifier successfully transmitted in the measurement
duration."
::= {dot11TransmitStreamReportEntry 11}
dot11TransmitStreamRprtMSDUDiscardedCount OBJECT-TYPE
SYNTAX Unsigned32
MAX-ACCESS read-only
STATUS current
DESCRIPTION
"This is a status variable.
It is written by the SME when a measurement report is completed.
This attribute indicates the number of MSDUs to the peer STA for the TC,
or TS given by the Traffic Identifier discarded due either to the number
of transmit attempts exceeding dot11ShortRetryLimit or dot11LongRetryLimit
as appropriate, or due to the MSDU lifetime having been reached."
::= {dot11TransmitStreamReportEntry 12}
dot11TransmitStreamRprtMSDUFailedCount OBJECT-TYPE
SYNTAX Unsigned32
MAX-ACCESS read-only
STATUS current
DESCRIPTION
"This is a status variable.
It is written by the SME when a measurement report is completed.
This attribute indicates the number of MSDUs to the peer STA for the TC,
or TS given by the Traffic Identifier discarded during the measurement
duration due to the number of transmit attempts exceeding
dot11ShortRetryLimit or dot11LongRetryLimit as appropriate."
::= {dot11TransmitStreamReportEntry 13}
dot11TransmitStreamRprtMultipleRetryCount OBJECT-TYPE
SYNTAX Unsigned32
MAX-ACCESS read-only
STATUS current
DESCRIPTION
"This is a status variable.
It is written by the SME when a measurement report is completed.
This attribute indicates the number of MSDUs for the TC, or TS given by
the Traffic Identifier that are successfully transmitted after more than
one retransmission attempt."
::= {dot11TransmitStreamReportEntry 14}
dot11TransmitStreamRprtCFPollsLostCount OBJECT-TYPE
SYNTAX Unsigned32
MAX-ACCESS read-only
STATUS current
DESCRIPTION
"This is a status variable.
It is written by the SME when a measurement report is completed.
This attribute indicates the number of QoS (+)CF-Poll frames transmitted
to the peer STA where there was no response from the QoS STA."
::= {dot11TransmitStreamReportEntry 15}
dot11TransmitStreamRprtBin0Range OBJECT-TYPE
SYNTAX Unsigned32
UNITS "TUs"
MAX-ACCESS read-only
STATUS current
DESCRIPTION
"This is a status variable.
It is written by the SME when a measurement report is completed.
This attribute indicates the delay range for Bin 0 of the delay histogram."
::= { dot11TransmitStreamReportEntry 16 }
dot11TransmitStreamRprtDelayHistogram OBJECT-TYPE
SYNTAX OCTET STRING (SIZE (6))
MAX-ACCESS read-only
STATUS current
DESCRIPTION
"This is a status variable.
It is written by the SME when a measurement report is completed.
This attribute indicates the histogram of delay of the frames (MSDUs) that
are successfully transmitted during the measurement duration for the indicated
Traffic Identifier and the indicated destination. Delay is measured
from the time the MSDU is passed to the MAC until the ACK is received from
the intermediate destination and is expressed in units of TUs. "
::= { dot11TransmitStreamReportEntry 17 }
dot11TransmitStreamRprtReason OBJECT-TYPE
SYNTAX INTEGER {
averageTrigger(0),
consecutiveTrigger(1),
delayTrigger(2) }
MAX-ACCESS read-only
STATUS current
DESCRIPTION
"This is a status variable.
It is written by the SME when a measurement report is completed.
This attribute indicates the Reason field indicating the reason that the
measuring QoS STA sent the Transmit Stream/Category measurement report."
DEFVAL { 0 }
::= { dot11TransmitStreamReportEntry 18 }
dot11TransmitStreamRprtVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11TransmitStreamReportEntry 19 }
dot11TransmitStreamRprtMeasurementMode OBJECT-TYPE
SYNTAX INTEGER {
success(0),
incapableBit(1),
refusedBit(2) }
MAX-ACCESS read-only
STATUS current
DESCRIPTION
"This is a status variable.
It is written by the SME when a measurement report is completed.
This attribute indicates the outcome status for the measurement request
which generated this measurement report; status is indicated using the
following reason codes: 1 indicates this STA is incapable of generating
the report, 2 indicates this STA is refusing to generate the report, 0
indicates the STA successfully carried out the measurement request."
DEFVAL { 0 }
::= { dot11TransmitStreamReportEntry 20 }
-- ********************************************************************
-- * End of dot11TransmitStreamReport TABLE
-- ********************************************************************
-- ********************************************************************
-- * Radio Measurement Configuration Information
-- ********************************************************************
dot11RMConfig OBJECT IDENTIFIER ::= { dot11RadioMeasurement 3 }
-- ********************************************************************
-- * dot11APChannelReport TABLE
-- ********************************************************************
dot11APChannelReportTable OBJECT-TYPE
SYNTAX SEQUENCE OF Dot11APChannelReportEntry
MAX-ACCESS not-accessible
STATUS current
DESCRIPTION
"AP Channel Report information, in tabular form."
::= { dot11RMConfig 1 }
dot11APChannelReportEntry OBJECT-TYPE
SYNTAX Dot11APChannelReportEntry
MAX-ACCESS not-accessible
STATUS current
DESCRIPTION
"An entry in the dot11APChannelReportTable. Each entry in the table is
indexed by dot11APChannelReportIndex."
INDEX { dot11APChannelReportIndex }
::= { dot11APChannelReportTable 1 }
Dot11APChannelReportEntry ::=
SEQUENCE {
dot11APChannelReportIndex Unsigned32,
dot11APChannelReportIfIndex InterfaceIndex,
dot11APChannelReportOperatingClass Unsigned32,
dot11APChannelReportChannelList OCTET STRING}
dot11APChannelReportIndex OBJECT-TYPE
SYNTAX Unsigned32
MAX-ACCESS not-accessible
STATUS current
DESCRIPTION
"Index for AP channel report entry in dot11APChannelReportTable, greater
than 0."
::= { dot11APChannelReportEntry 1 }
dot11APChannelReportIfIndex OBJECT-TYPE
SYNTAX InterfaceIndex
MAX-ACCESS read-create
STATUS current
DESCRIPTION
"This is a status variable.
It is written by the SME when a measurement report is completed.
The ifIndex for this row of the AP channel report."
::= { dot11APChannelReportEntry 2 }
dot11APChannelReportOperatingClass OBJECT-TYPE
SYNTAX Unsigned32(1..255)
MAX-ACCESS read-create
STATUS current
DESCRIPTION
"This is a status variable.
It is written by the SME when a measurement report is completed.
This attribute indicates the channel set for this AP Channel Report. Country,
Operating Class and Channel Number together specify the channel frequency
and spacing for this measurement report. Valid values of Operating
Class are shown in Annex E."
REFERENCE "Annex E"
::= { dot11APChannelReportEntry 3 }
dot11APChannelReportChannelList OBJECT-TYPE
SYNTAX OCTET STRING (SIZE(0..255))
MAX-ACCESS read-create
STATUS current
DESCRIPTION
"This is a status variable.
It is written by the SME when a measurement report is completed.
This attribute lists the specific channels in this AP Channel Report. The
default value is null. Each octet indicates a different channel within the
indicated Operating Class. This list of channels is the Channel List in
the AP Channel Report element described in 8.4.2.38. "
DEFVAL { ''H }
::= { dot11APChannelReportEntry 4 }
-- ********************************************************************
-- * End of dot11APChannelReportTable TABLE
-- ********************************************************************
-- ********************************************************************
-- * dot11RMNeighborReport TABLE
-- ********************************************************************
dot11RMNeighborReportNextIndex OBJECT-TYPE
SYNTAX Unsigned32(0..255)
MAX-ACCESS not-accessible
STATUS current
DESCRIPTION
"Identifies the next available index for managing the neighbor report
table. If this attribute is 0, it indicates that the neighbor report feature
is not configurable via SNMP, or the table is full and new rows cannot
be accepted."
::= { dot11RMConfig 2 }
dot11RMNeighborReportTable OBJECT-TYPE
SYNTAX SEQUENCE OF Dot11RMNeighborReportEntry
MAX-ACCESS not-accessible
STATUS current
DESCRIPTION
"This table contains pertinent information on a collection of BSSID's that
are candidates to which STAs can roam. The rows are created using create-
AndWait method and fill in the attributes. When the rowStatus is set to
active, the row can be included in Neighbor Report elements. If there is
an error, the rowStatus is set to notReady by SME. Since this table contains
all Neighbor Report element entries for all interfaces enabled with
the neighbor report feature, it is possible to have too many entries for
one interface, while still remaining under the MaxTableSize. In that situation,
SME includes neighbor report entries only with lower
dot11RMNeighborReportIFIndex up to the maximum possible number of entries
for a particular interface identified by ifIndex. SME sets the rowStatus
to notInService for those rows that cannot be included in the Neighbor
Report element for that interface."
::= { dot11RMConfig 3 }
dot11RMNeighborReportEntry OBJECT-TYPE
SYNTAX Dot11RMNeighborReportEntry
MAX-ACCESS not-accessible
STATUS current
DESCRIPTION
"An entry in the dot11RMNeighborReportTable"
INDEX { dot11RMNeighborReportIndex }
::= { dot11RMNeighborReportTable 1 }
Dot11RMNeighborReportEntry ::=
SEQUENCE {
dot11RMNeighborReportIndex Unsigned32,
dot11RMNeighborReportIfIndex InterfaceIndex,
dot11RMNeighborReportBSSID MacAddress,
dot11RMNeighborReportAPReachability INTEGER,
dot11RMNeighborReportSecurity TruthValue,
dot11RMNeighborReportCapSpectrumMgmt TruthValue,
dot11RMNeighborReportCapQoS TruthValue,
dot11RMNeighborReportCapAPSD TruthValue,
dot11RMNeighborReportCapRM TruthValue,
dot11RMNeighborReportCapDelayBlockAck TruthValue,
dot11RMNeighborReportCapImmediateBlockAck TruthValue,
dot11RMNeighborReportKeyScope TruthValue,
dot11RMNeighborReportOperatingClass Unsigned32,
dot11RMNeighborReportChannelNumber Unsigned32,
dot11RMNeighborReportPhyType INTEGER,
dot11RMNeighborReportNeighborTSFInfo OCTET STRING,
dot11RMNeighborReportPilotInterval Unsigned32,
dot11RMNeighborReportPilotMultipleBSSID OCTET STRING,
dot11RMNeighborReportRMEnabledCapabilities OCTET STRING,
dot11RMNeighborReportVendorSpecific OCTET STRING,
dot11RMNeighborReportRowStatus RowStatus,
dot11RMNeighborReportMobilityDomain TruthValue,
dot11RMNeighborReportCapHT TruthValue,
dot11RMNeighborReportHTLDPCCodingCap TruthValue,
dot11RMNeighborReportHTSupportedChannelWidthSet
TruthValue,
dot11RMNeighborReportHTSMPowerSave Unsigned32,
dot11RMNeighborReportHTGreenfield TruthValue,
dot11RMNeighborReportHTShortGIfor20MHz TruthValue,
dot11RMNeighborReportHTShortGIfor40MHz TruthValue,
dot11RMNeighborReportHTTxSTBC TruthValue,
dot11RMNeighborReportHTRxSTBC Unsigned32,
dot11RMNeighborReportHTDelayedBlockAck TruthValue,
dot11RMNeighborReportHTMaxAMSDULength TruthValue,
dot11RMNeighborReportHTDSSCCKModein40MHz TruthValue,
dot11RMNeighborReportHTFortyMHzIntolerant TruthValue,
dot11RMNeighborReportHTLSIGTXOPProtectionSupport TruthValue,
dot11RMNeighborReportHTMaxAMPDULengthExponent Unsigned32,
dot11RMNeighborReportHTMinMPDUStartSpacing Unsigned32,
dot11RMNeighborReportHTRxMCSBitMask OCTET STRING,
dot11RMNeighborReportHTRxHighestSupportedDataRate Unsigned32,
dot11RMNeighborReportHTTxMCSSetDefined TruthValue,
dot11RMNeighborReportHTTxRxMCSSetNotEqual TruthValue,
dot11RMNeighborReportHTTxMaxNumberSpatialStreamsSupported
Unsigned32,
dot11RMNeighborReportHTTxUnequalModulationSupported
TruthValue,
dot11RMNeighborReportHTPCO TruthValue,
dot11RMNeighborReportHTPCOTransitionTime Unsigned32,
dot11RMNeighborReportHTMCSFeedback Unsigned32,
dot11RMNeighborReportHTCSupport TruthValue,
dot11RMNeighborReportHTRDResponder TruthValue,
dot11RMNeighborReportHTImplictTransmitBeamformingReceivingCap
TruthValue,
dot11RMNeighborReportHTReceiveStaggeredSoundingCap
TruthValue,
dot11RMNeighborReportHTTransmitStaggeredSoundingCap
TruthValue,
dot11RMNeighborReportHTReceiveNDPCap TruthValue,
dot11RMNeighborReportHTTransmitNDPCap TruthValue,
dot11RMNeighborReportHTImplicitTransmitBeamformingCap
TruthValue,
dot11RMNeighborReportHTTransmitBeamformingCalibration
Unsigned32,
dot11RMNeighborReportHTExplicitCSITransmitBeamformingCap
TruthValue,
dot11RMNeighborReportHTExplicitNonCompressedSteeringCap
TruthValue,
dot11RMNeighborReportHTExplicitCompressedSteeringCap
TruthValue,
dot11RMNeighborReportHTExplicitTransmitBeamformingFeedback
Unsigned32,
dot11RMNbRprtHTExplicitNonCompressedBeamformingFeedbackCap
Unsigned32,
dot11RMNeighborReportHTExplicitCompressedBeamformingFeedbackCap
Unsigned32,
dot11RMNeighborReportHTTransmitBeamformingMinimalGrouping
Unsigned32,
dot11RMNbRprtHTCSINumberofTxBeamformingAntennasSuppt
Unsigned32,
dot11RMNbRprtHTNonCompressedSteeringNumofTxBmfmingAntennasSuppt
Unsigned32,
dot11RMNbRprtHTCompressedSteeringNumberofTxBmfmingAntennasSuppt
Unsigned32,
dot11RMNbRprtHTCSIMaxNumberofRowsTxBeamformingSuppt
Unsigned32,
dot11RMNeighborReportHTTransmitBeamformingChannelEstimationCap
Unsigned32,
dot11RMNeighborReportHTAntSelectionCap TruthValue,
dot11RMNeighborReportHTExplicitCSIFeedbackBasedTxASELCap
TruthValue,
dot11RMNeighborReportHTAntIndicesFeedbackBasedTxASELCap
TruthValue,
dot11RMNeighborReportHTExplicitCSIFeedbackBasedCap
TruthValue,
dot11RMNeighborReportHTAntIndicesFeedbackCap TruthValue,
dot11RMNeighborReportHTRxASELCap TruthValue,
dot11RMNeighborReportHTTxSoundingPPDUsCap TruthValue,
dot11RMNeighborReportHTInfoPrimaryChannel Unsigned32,
dot11RMNeighborReportHTInfoSecChannelOffset Unsigned32,
dot11RMNeighborReportHTInfoSTAChannelWidth TruthValue,
dot11RMNeighborReportHTInfoRIFSMode TruthValue,
dot11RMNeighborReportHTInfoProtection Unsigned32,
dot11RMNeighborReportHTInfoNonGreenfieldHTSTAsPresent
TruthValue,
dot11RMNeighborReportHTInfoOBSSNonHTSTAsPresent
TruthValue,
dot11RMNeighborReportHTInfoDualBeacon TruthValue,
dot11RMNeighborReportHTInfoDualCTSProtection TruthValue,
dot11RMNeighborReportHTInfoSTBCBeacon TruthValue,
dot11RMNeighborReportHTInfoLSIGTXOPProtectionSup
TruthValue,
dot11RMNeighborReportHTInfoPCOActive TruthValue,
dot11RMNeighborReportHTInfoPCOPhase TruthValue,
dot11RMNeighborReportHTInfoBasicMCSSet OCTET STRING,
dot11RMNeighborReportHTSecChannelOffset Unsigned32,
dot11RMNeighborReportExtCapPSMPSupport TruthValue,
dot11RMNeighborReportExtCapSPSMPSup TruthValue,
dot11RMNeighborReportExtCapServiceIntervalGranularity
Unsigned32,
dot11RMNeighborReportBSSTransitCandPreference Unsigned32,
dot11RMNeighborReportBSSTerminationTSF TSFType,
dot11RMNeighborReportBSSTerminationDuration Unsigned32
}
dot11RMNeighborReportIndex OBJECT-TYPE
SYNTAX Unsigned32
MAX-ACCESS not-accessible
STATUS current
DESCRIPTION
"Index for neighbor report configuration table in
dot11RMNeighborReportTable, greater than 0."
::= { dot11RMNeighborReportEntry 1 }
dot11RMNeighborReportIfIndex OBJECT-TYPE
SYNTAX InterfaceIndex
MAX-ACCESS read-create
STATUS current
DESCRIPTION
"This is a status variable.
It is written by the SME when a measurement report is completed.
The ifIndex for this row of the neighbor report."
::= { dot11RMNeighborReportEntry 2 }
dot11RMNeighborReportBSSID OBJECT-TYPE
SYNTAX MacAddress
MAX-ACCESS read-write
STATUS current
DESCRIPTION
"This is a status variable.
It is written by the SME when a measurement report is completed.
This attribute indicates the BSSID of the AP described by this row of
neighbor report."
::= { dot11RMNeighborReportEntry 3 }
dot11RMNeighborReportAPReachability OBJECT-TYPE
SYNTAX INTEGER { notReachable(1), unknown(2), reachable(3) }
MAX-ACCESS read-create
STATUS current
DESCRIPTION
"This is a status variable.
It is written by the SME when a measurement report is completed.
This attribute indicates the reachability of the AP represented by the
dot11NeighborReportBSSID."
::= { dot11RMNeighborReportEntry 4 }
dot11RMNeighborReportSecurity OBJECT-TYPE
SYNTAX TruthValue
MAX-ACCESS read-create
STATUS current
DESCRIPTION
"This is a status variable.
It is written by the SME when a measurement report is completed.
This attribute, when true, indicates that the neighbor AP identified by
this BSSID supports the same security provisioning as used by the AP which
provided this neighbor report. This attribute, when false, indicates
either that the neighbor AP identified by this BSSID does not support the
same security provisioning or that the security information for this
neighbor AP is not available at this time."
::= { dot11RMNeighborReportEntry 5 }
dot11RMNeighborReportCapSpectrumMgmt OBJECT-TYPE
SYNTAX TruthValue
MAX-ACCESS read-create
STATUS current
DESCRIPTION
"This is a status variable.
It is written by the SME when a measurement report is completed.
This attribute indicates the spectrum management capability of the AP represented
by dot11NeighborReportBSSID."
::= { dot11RMNeighborReportEntry 6 }
dot11RMNeighborReportCapQoS OBJECT-TYPE
SYNTAX TruthValue
MAX-ACCESS read-write
STATUS current
DESCRIPTION
"This is a status variable.
It is written by the SME when a measurement report is completed.
This attribute indicates the QoS capability of the AP represented by
dot11NeighborReportBSSID."
::= { dot11RMNeighborReportEntry 7 }
dot11RMNeighborReportCapAPSD OBJECT-TYPE
SYNTAX TruthValue
MAX-ACCESS read-create
STATUS current
DESCRIPTION
"This is a status variable.
It is written by the SME when a measurement report is completed.
This attribute indicates the APSD capability of the AP represented by
dot11NeighborReportBSSID."
::= { dot11RMNeighborReportEntry 8 }
dot11RMNeighborReportCapRM OBJECT-TYPE
SYNTAX TruthValue
MAX-ACCESS read-create
STATUS current
DESCRIPTION
"This is a status variable.
It is written by the SME when a measurement report is completed.
This attribute indicates the RM capability of the AP represented by
dot11NeighborReportBSSID."
::= { dot11RMNeighborReportEntry 9 }
dot11RMNeighborReportCapDelayBlockAck OBJECT-TYPE
SYNTAX TruthValue
MAX-ACCESS read-create
STATUS current
DESCRIPTION
"This is a status variable.
It is written by the SME when a measurement report is completed.
This attribute indicates the Delayed BlockAck capability of the AP represented
by dot11NeighborReportBSSID."
::= { dot11RMNeighborReportEntry 10 }
dot11RMNeighborReportCapImmediateBlockAck OBJECT-TYPE
SYNTAX TruthValue
MAX-ACCESS read-create
STATUS current
DESCRIPTION
"This is a status variable.
It is written by the SME when a measurement report is completed.
This attribute indicates the Immediate BlockAck capability of the AP represented
by dot11NeighborReportBSSID."
::= { dot11RMNeighborReportEntry 11 }
dot11RMNeighborReportKeyScope OBJECT-TYPE
SYNTAX TruthValue
MAX-ACCESS read-create
STATUS current
DESCRIPTION
"This is a status variable.
It is written by the SME when a measurement report is completed.
This attribute, when true, indicates the neighbor AP identified by this
BSSID has the same authenticator as the AP which provided this neighbor
report. This attribute, when false, indicates that the neighbor AP identified 
by this BSSID has a different authenticator or that authenticator
information is not available."
::= { dot11RMNeighborReportEntry 12 }
dot11RMNeighborReportOperatingClass OBJECT-TYPE
SYNTAX Unsigned32(1..255)
MAX-ACCESS read-create
STATUS current
DESCRIPTION
"This is a status variable.
It is written by the SME when a measurement report is completed.
This attribute indicates the channel set for this neighbor report entry.
Country, Operating Class and Channel Number together specify the channel
frequency and spacing for this measurement report. Valid values of Operating
Class are shown in Annex E."
REFERENCE
"Annex E"
::= { dot11RMNeighborReportEntry 13 }
dot11RMNeighborReportChannelNumber OBJECT-TYPE
SYNTAX Unsigned32 (1..255)
MAX-ACCESS read-create
STATUS current
DESCRIPTION
"This is a status variable.
It is written by the SME when a measurement report is completed.
This attribute indicates the current operating channel of the AP represented
by the dot11NeighborReportBSSID. The Channel Number is only defined
within the indicated Operating Class for this neighbor report entry."
::= { dot11RMNeighborReportEntry 14 }
dot11RMNeighborReportPhyType OBJECT-TYPE
SYNTAX INTEGER {
fhss(1),
dsss(2),
irbaseband(3),
ofdm(4),
hrdsss(5),
erp(6),
ht(7) }
UNITS "dot11PHYType"
MAX-ACCESS read-create
STATUS current
DESCRIPTION
"This is a status variable.
It is written by the SME when a measurement report is completed.
This attribute indicates the PHY Type of the neighbor AP identified by
this BSSID."
::= { dot11RMNeighborReportEntry 15 }
dot11RMNeighborReportNeighborTSFInfo OBJECT-TYPE
SYNTAX OCTET STRING (SIZE (6))
MAX-ACCESS read-create
STATUS current
DESCRIPTION
"This is a status variable.
It is written by the SME when a measurement report is completed.
This attribute indicates TSF timing information for the neighbor AP identified
by this BSSID. The TSF timing information includes the TSF Offset
and the Beacon Interval, as defined in 8.4.2.39."
::= { dot11RMNeighborReportEntry 16 }
dot11RMNeighborReportPilotInterval OBJECT-TYPE
SYNTAX Unsigned32
UNITS "TUs"
MAX-ACCESS read-create
STATUS current
DESCRIPTION
"This is a status variable.
It is written by the SME when a measurement report is completed.
This attribute indicates Measurement Pilot Interval for the neighbor AP
identified by this BSSID, as defined in 8.4.1.18."
::= { dot11RMNeighborReportEntry 17 }
dot11RMNeighborReportPilotMultipleBSSID OBJECT-TYPE
SYNTAX OCTET STRING (SIZE(1))
UNITS "BSSID LSBs"
MAX-ACCESS read-create
STATUS current
DESCRIPTION
"This is a status variable.
It is written by the SME when a measurement report is completed.
This attribute indicates n, where 2**n is the maximum number of BSSIDs in
the multiple BSSID set, as described in 10.11.14."
::= { dot11RMNeighborReportEntry 18 }
dot11RMNeighborReportRMEnabledCapabilities OBJECT-TYPE
SYNTAX OCTET STRING (SIZE(7))
MAX-ACCESS read-create
STATUS current
DESCRIPTION
"This is a status variable.
It is written by the SME when a measurement report is completed.
This attribute indicates the detailed enabled capabilities of the AP represented
by the dot11NeighborReportBSSID, as defined in 8.4.2.47."
REFERENCE
"IEEE 802.11 - 8.4.2.47"
::= { dot11RMNeighborReportEntry 19 }
dot11RMNeighborReportVendorSpecific OBJECT-TYPE
SYNTAX OCTET STRING (SIZE(0..255))
MAX-ACCESS read-create
STATUS current
DESCRIPTION
"This is a status variable.
It is written by the SME when a measurement report is completed.
This attribute provides an envelope for any optional vendor specific subelements
which may be included in a measurement report element. The
default value is null."
DEFVAL { ''H }
::= { dot11RMNeighborReportEntry 20 }
dot11RMNeighborReportRowStatus OBJECT-TYPE
SYNTAX RowStatus
MAX-ACCESS read-create
STATUS current
DESCRIPTION
"This is a status variable.
It is written by the SME when a measurement report is completed.
Contains the row status of the neighbor report, essentially used for indicating
whether the row has all valid attributes filled in. Then set to
active to be used in Neighbor Report elements. If any parameter is
invalid, the SME sets this attribute back to notReady. It is the responsibility
of the manager to correct the parameters."
::= { dot11RMNeighborReportEntry 21 }
dot11RMNeighborReportMobilityDomain OBJECT-TYPE
SYNTAX TruthValue
MAX-ACCESS read-create
STATUS current
DESCRIPTION
"This is a status variable.
It is written by the SME when a measurement report is completed.
Indicates a common mobility domain identifier (MDID) and an identical
value of the FT Capability and Policy value."
::= { dot11RMNeighborReportEntry 22 }
dot11RMNeighborReportCapHT OBJECT-TYPE
SYNTAX TruthValue
MAX-ACCESS read-create
STATUS current
DESCRIPTION
"This is a status variable.
It is written by the SME when a measurement report is completed.
The High Throughput Bit when equal to 1 indicates that the AP represented
by this BSSID is an HT AP including the HT Capabilities element in its
Beacons and that the contents of that HT Capabilities element are identical
to the HT Capabilities element advertised by the AP sending the
report. See 8.4.2.39"
::= { dot11RMNeighborReportEntry 23 }
dot11RMNeighborReportHTLDPCCodingCap OBJECT-TYPE
SYNTAX TruthValue
MAX-ACCESS read-create
STATUS current
DESCRIPTION
"This is a status variable.
It is written by the SME when a measurement report is completed.
The HT LDPC coding capability indicates support for receiving LDPC coded
packets, equal to false if not supported, equal to true if supported. See
8.4.2.58.2"
::= { dot11RMNeighborReportEntry 24 }
dot11RMNeighborReportHTSupportedChannelWidthSet OBJECT-TYPE
SYNTAX TruthValue
MAX-ACCESS read-create
STATUS current
DESCRIPTION
"This is a status variable.
It is written by the SME when a measurement report is completed.
The HT Supported channel width set indicates which channel widths the STA
supports, equal to false if only 20 MHz operation is supported, equal to
true if both 20 MHz and 40 MHz operation is supported. See 8.4.2.58.2"
::= { dot11RMNeighborReportEntry 25 }
dot11RMNeighborReportHTSMPowerSave OBJECT-TYPE
SYNTAX Unsigned32 (0..3)
MAX-ACCESS read-create
STATUS current
DESCRIPTION
"This is a status variable.
It is written by the SME when a measurement report is completed.
The HT SM Power Save indicates the SM power save mode, equal to 0 for
static SM power save mode, equal to 1 for dynamic SM power save mode,
equal to 3 for SM power save disabled, the value 2 is reserved; see
8.4.2.58.2"
::= { dot11RMNeighborReportEntry 26 }
dot11RMNeighborReportHTGreenfield OBJECT-TYPE
SYNTAX TruthValue
MAX-ACCESS read-create
STATUS current
DESCRIPTION
"This is a status variable.
It is written by the SME when a measurement report is completed.
The HT-greenfield indicates support for the reception of PPDUs with HTgreenfield
format, equal to false if not supported, equal to true if supported.
See 8.4.2.58.2"
::= { dot11RMNeighborReportEntry 27 }
dot11RMNeighborReportHTShortGIfor20MHz OBJECT-TYPE
SYNTAX TruthValue
MAX-ACCESS read-create
STATUS current
DESCRIPTION
"This is a status variable.
It is written by the SME when a measurement report is completed.
The HT Short GI for 20 MHZ indicates short GI support for the reception of
20 MHz packets, equal to false if not supported, equal to true if supported
See 8.4.2.58.2"
::= { dot11RMNeighborReportEntry 28 }
dot11RMNeighborReportHTShortGIfor40MHz OBJECT-TYPE
SYNTAX TruthValue
MAX-ACCESS read-create
STATUS current
DESCRIPTION
"This is a status variable.
It is written by the SME when a measurement report is completed.
The HT Short GI for 40 MHz indicates short GI support for the reception of
40 MHz packets, equal to false if not supported, equal to true if supported.
See 8.4.2.58.2"
::= { dot11RMNeighborReportEntry 29}
dot11RMNeighborReportHTTxSTBC OBJECT-TYPE
SYNTAX TruthValue
MAX-ACCESS read-create
STATUS current
DESCRIPTION
"This is a status variable.
It is written by the SME when a measurement report is completed.
The HT Tx STBC indicates support for the transmission of PPDUs using STBC,
equal to false if not supported, equal to true if supported. See
8.4.2.58.2"
::= { dot11RMNeighborReportEntry 30}
dot11RMNeighborReportHTRxSTBC OBJECT-TYPE
SYNTAX Unsigned32
MAX-ACCESS read-create
STATUS current
DESCRIPTION
"This is a status variable.
It is written by the SME when a measurement report is completed.
The HT Rx STBC indicates support for the reception of PPDUs using STBC,
equal to 0 for no support, equal to 1 for support of one spatial stream,
equal to 2 for support of one and two spatial streams, equal to 3 for support
of one, two, and three spatial streams. See 8.4.2.58.2"
::= { dot11RMNeighborReportEntry 31}
dot11RMNeighborReportHTDelayedBlockAck OBJECT-TYPE
SYNTAX TruthValue
MAX-ACCESS read-create
STATUS current
DESCRIPTION
"This is a status variable.
It is written by the SME when a measurement report is completed.
The HT-delayed Block ACK indicates support for HT-delayed Block ACK operation,
equal to false if not supported, equal to true if supported. Support
indicates that the STA is able to accept an ADDBA request for HTdelayed
Block ACK. See 8.4.2.58.2"
::= { dot11RMNeighborReportEntry 32 }
dot11RMNeighborReportHTMaxAMSDULength OBJECT-TYPE
SYNTAX TruthValue
MAX-ACCESS read-create
STATUS current
DESCRIPTION
"This is a status variable.
It is written by the SME when a measurement report is completed.
The HT Maximum A-MSDU length indicates maximum A-MSDU length, equal to
false for 3839 octets, equal to true for 7935 octets. See 8.4.2.58.2"
::= { dot11RMNeighborReportEntry 33 }
dot11RMNeighborReportHTDSSCCKModein40MHz OBJECT-TYPE
SYNTAX TruthValue
MAX-ACCESS read-create
STATUS current
DESCRIPTION
"This is a status variable.
It is written by the SME when a measurement report is completed.
The HT DSSS/CCK Mode in 40 MHz indicates use of DSSS/CCK mode in a 40 MHz
capable BSS operating in 20/40 MHz mode, equal to false if DSSS/CCK in 40
MHz is not allowed, equal to true if the DSSS/CCK in 40 MHz is allowed.
See 8.4.2.58.2"
::= { dot11RMNeighborReportEntry 34 }
dot11RMNeighborReportHTFortyMHzIntolerant OBJECT-TYPE
SYNTAX TruthValue
MAX-ACCESS read-create
STATUS current
DESCRIPTION
"This is a status variable.
It is written by the SME when a measurement report is completed.
The HT Forty MHz Intolerant indicates whether other BSSs receiving this
information are required to prohibit 40 MHz transmissions, equal to true
to prohibit 20/40 MHz BSS operation, otherwise equal to false. See
8.4.2.58.2"
::= { dot11RMNeighborReportEntry 35 }
dot11RMNeighborReportHTLSIGTXOPProtectionSupport OBJECT-TYPE
SYNTAX TruthValue
MAX-ACCESS read-create
STATUS current
DESCRIPTION
"This is a status variable.
It is written by the SME when a measurement report is completed.
The HT L-SIG TXOP protection support indicates support for the LSIG TXOP
protection mechanism, equal to false if not supported, equal to true if
supported. See 8.4.2.58.2"
::= { dot11RMNeighborReportEntry 36 }
dot11RMNeighborReportHTMaxAMPDULengthExponent OBJECT-TYPE
SYNTAX Unsigned32 (0..3)
MAX-ACCESS read-create
STATUS current
DESCRIPTION
"This is a status variable.
It is written by the SME when a measurement report is completed.
The HT Maximum A-MPDU Length Exponent indicates the maximum length of AMPDU
that the STA can receive. This field is an integer in the range 0 to
3. The length defined by this field is equal to 2(13 + Maximum A-MPDU
Length) - 1 octets. See 8.4.2.58.3"
::= { dot11RMNeighborReportEntry 37 }
dot11RMNeighborReportHTMinMPDUStartSpacing OBJECT-TYPE
SYNTAX Unsigned32 (0..7)
MAX-ACCESS read-create
STATUS current
DESCRIPTION
"This is a status variable.
It is written by the SME when a measurement report is completed.
The HT Minimum MPDU Start Spacing determines the minimum time between the
start of adjacent MPDUs within an AMPDU, measured at the PHY-SAP, equal to
0 for no restriction, equal to 1 for 1/4 microsecond, equal to 2 for 1/2
microsecond, equal to 3 for 1 microsecond, equal to 4 for 2 microseconds,
equal to 5 for 4 microseconds, equal to 6 for 8 microseconds, equal to 7
for 16 microseconds. See 8.4.2.58.3"
::= { dot11RMNeighborReportEntry 38 }
dot11RMNeighborReportHTRxMCSBitMask OBJECT-TYPE
SYNTAX OCTET STRING (SIZE(10))
MAX-ACCESS read-create
STATUS current
DESCRIPTION
"This is a status variable.
It is written by the SME when a measurement report is completed.
The HT Rx MCS Bitmask is a 77 bit subfield that defines a set of MCS values,
where bit B0 (i.e., the lsb of the first octet) corresponds to MCS 0
and bit B76 corresponds to MCS 76, equal to 0 when the MCS is not supported,
equal to 1 when the MCS is supported. See 8.4.2.58.4"
::= { dot11RMNeighborReportEntry 39}
dot11RMNeighborReportHTRxHighestSupportedDataRate OBJECT-TYPE
SYNTAX Unsigned32
MAX-ACCESS read-create
STATUS current
DESCRIPTION
"This is a status variable.
It is written by the SME when a measurement report is completed.
The HT Highest Supported Data Rate is a 10 bit subfield that defines the
highest data rate that the STA is able to receive, in units of 1 Mb/s,
where 1 represents 1 Mb/s, and incrementing by 1 Mb/s steps to the value
1023, which represents 1023 Mb/s. See 8.4.2.58.4"
::= { dot11RMNeighborReportEntry 40 }
dot11RMNeighborReportHTTxMCSSetDefined OBJECT-TYPE
SYNTAX TruthValue
MAX-ACCESS read-create
STATUS current
DESCRIPTION
"This is a status variable.
It is written by the SME when a measurement report is completed.
The HT Tx MCS Set Defined indicates if the Tx MCS set is defined, equal to
false if no Tx MCS set is defined, equal to true if Tx MCS set is defined.
See 8.4.2.58.4"
::= { dot11RMNeighborReportEntry 41 }
dot11RMNeighborReportHTTxRxMCSSetNotEqual OBJECT-TYPE
SYNTAX TruthValue
MAX-ACCESS read-create
STATUS current
DESCRIPTION
"This is a status variable.
It is written by the SME when a measurement report is completed.
The HT Tx RX MCS set not equal indicates if the Tx MCS set is defined to
be equal to the Rx MCS set, equal to false where no Tx MCS set is defined
or where the Tx MCS Set is defined to be equal to the RX MCS Set, equal to
true where the TX MCS set may differ from the Rx MCS set. See 8.4.2.58.4"
::= { dot11RMNeighborReportEntry 42 }
dot11RMNeighborReportHTTxMaxNumberSpatialStreamsSupported OBJECT-TYPE
SYNTAX Unsigned32 (0..3)
MAX-ACCESS read-create
STATUS current
DESCRIPTION
"This is a status variable.
It is written by the SME when a measurement report is completed.
The HT Tx maximum number spatial streams supported indicates maximum number
of spatial streams supported when the Tx MCS Set may differ from the
Rx MCS set, equal to 0 where no TX MCS set is defined or where the Tx MCS
set is defined to be equal to the RX MCS set or where the maximum number
of spatial streams supported when transmitting is 1 spatial stream and the
Tx MCS set may differ from the Rx MCS set, equal to 1 where the maximum
number of spatial streams supported when transmitting is 2 spatial streams
and the Tx MCS set may differ from the Rx MCS set, equal to 2 where the
maximum number of spatial streams supported when transmitting is 3 spatial
streams and the Tx MCS set may differ from the Rx MCS set, equal to 3 where
the maximum number of spatial streams supported when transmitting is 4
spatial streams and the Tx MCS set may differ from the Rx MCS set. See
8.4.2.58.4"
::= { dot11RMNeighborReportEntry 43 }
dot11RMNeighborReportHTTxUnequalModulationSupported OBJECT-TYPE
SYNTAX TruthValue
MAX-ACCESS read-create
STATUS current
DESCRIPTION
"This is a status variable.
It is written by the SME when a measurement report is completed.
The HT Tx UEQM supported indicates whether transmit UEQM is supported when
the Tx MCS set may differ from the Rx MCS set, equal to false where no TX
MCS set is defined or where the Tx MCS set is defined to be equal to the
RX MCS set or when UEQM is not supported and the Tx MCS set may differ from
the Rx MCS set, equal to true when UEQM is supported and the Tx MCS set may
differ from the Rx MCS set. See 8.4.2.58.4"
::= { dot11RMNeighborReportEntry 44 }
dot11RMNeighborReportHTPCO OBJECT-TYPE
SYNTAX TruthValue
MAX-ACCESS read-create
STATUS current
DESCRIPTION
"This is a status variable.
It is written by the SME when a measurement report is completed.
The HT PCO indicates support for PCO, equal to false if not supported,
equal to true if supported. See 8.4.2.58.5"
::= { dot11RMNeighborReportEntry 45 }
dot11RMNeighborReportHTPCOTransitionTime OBJECT-TYPE
SYNTAX Unsigned32 (0..3)
MAX-ACCESS read-create
STATUS current
DESCRIPTION
"This is a status variable.
It is written by the SME when a measurement report is completed.
The HT PCO transition time indicates that the STA can switch between 20
MHz channel width and 40 MHz channel width within the indicated time,
equal to 0 for no transition, equal to 1 for 400 microseconds, equal to 2
for 1.5 ms, equal to 3 for 5 ms. For the no transition case (equal to 0)
the PCO active STA does not change its operation channel width and is able
to receive 40 MHz PPDUs during the 20 MHz phase. See 8.4.2.58.5"
::= { dot11RMNeighborReportEntry 46 }
dot11RMNeighborReportHTMCSFeedback OBJECT-TYPE
SYNTAX Unsigned32 (0..3)
MAX-ACCESS read-create
STATUS current
DESCRIPTION
"This is a status variable.
It is written by the SME when a measurement report is completed.
The HT MFB indicates the capability of the STA to provide MFB, equal to 0
if the STA does not provide MFB, equal to 2 if the STA provide only unsolicited
MFB, equal to 3 if the STA can provide MFB in response to MRQ as
well as unsolicited MFB. Note the value 1 is reserved. See 8.4.2.58.5"
::= { dot11RMNeighborReportEntry 47 }
dot11RMNeighborReportHTCSupport OBJECT-TYPE
SYNTAX TruthValue
MAX-ACCESS read-create
STATUS current
DESCRIPTION
"This is a status variable.
It is written by the SME when a measurement report is completed.
The HT +HTC support indicates support of the HT Control field, equal to
false if not supported, equal to true if supported. See 8.4.2.58.5"
::= { dot11RMNeighborReportEntry 48 }
dot11RMNeighborReportHTRDResponder OBJECT-TYPE
SYNTAX TruthValue
MAX-ACCESS read-create
STATUS current
DESCRIPTION
"This is a status variable.
It is written by the SME when a measurement report is completed.
The HT RD responder indicates support for acting as a revere direction
responder, equal to false if not supported, equal to true if supported.
See 8.4.2.58.5"
::= { dot11RMNeighborReportEntry 49}
dot11RMNeighborReportHTImplictTransmitBeamformingReceivingCap OBJECT-TYPE
SYNTAX TruthValue
MAX-ACCESS read-create
STATUS current
DESCRIPTION
"This is a status variable.
It is written by the SME when a measurement report is completed.
The HT implicit Transmit Beamforming receiving capable indicates whether
this STA can receive Transmit Beamforming steered frames using implicit
feedback, equal to false if not supported, equal to true if supported. See
8.4.2.58.6"
::= { dot11RMNeighborReportEntry 50 }
dot11RMNeighborReportHTReceiveStaggeredSoundingCap OBJECT-TYPE
SYNTAX TruthValue
MAX-ACCESS read-create
STATUS current
DESCRIPTION
"This is a status variable.
It is written by the SME when a measurement report is completed.
The HT receive staggered sounding capable indicates whether this STA can
receive staggered sounding frames, equal to false if not supported, equal
to true if supported. See 8.4.2.58.6"
::= { dot11RMNeighborReportEntry 51 }
dot11RMNeighborReportHTTransmitStaggeredSoundingCap OBJECT-TYPE
SYNTAX TruthValue
MAX-ACCESS read-create
STATUS current
DESCRIPTION
"This is a status variable.
It is written by the SME when a measurement report is completed.
The HT transmit staggered sounding capable indicates whether this STA can
transmit staggered sounding frames, equal to false if not supported, equal
to true if supported. See 8.4.2.58.6"
::= { dot11RMNeighborReportEntry 52 }
dot11RMNeighborReportHTReceiveNDPCap OBJECT-TYPE
SYNTAX TruthValue
MAX-ACCESS read-create
STATUS current
DESCRIPTION
"This is a status variable.
It is written by the SME when a measurement report is completed.
The HT Receive NDP capable indicates whether this receiver can interpret
NDPs as sounding frames, equal to false if not supported, equal to true if
supported. See 8.4.2.58.6"
::= { dot11RMNeighborReportEntry 53 }
dot11RMNeighborReportHTTransmitNDPCap OBJECT-TYPE
SYNTAX TruthValue
MAX-ACCESS read-create
STATUS current
DESCRIPTION
"This is a status variable.
It is written by the SME when a measurement report is completed.
The HT Transmit NDP capable indicates whether this STA can transmit NDPs
as sounding frames, equal to false if not supported, equal to true if supported.
See 8.4.2.58.6"
::= { dot11RMNeighborReportEntry 54 }
dot11RMNeighborReportHTImplicitTransmitBeamformingCap OBJECT-TYPE
SYNTAX TruthValue
MAX-ACCESS read-create
STATUS current
DESCRIPTION
"This is a status variable.
It is written by the SME when a measurement report is completed.
The HT Implicit Transmit Beamforming capable indicates whether this STA
can apply implicit transmit beamforming, equal to false if not supported,
equal to true if supported. See 8.4.2.58.6"
::= { dot11RMNeighborReportEntry 55 }
dot11RMNeighborReportHTTransmitBeamformingCalibration OBJECT-TYPE
SYNTAX Unsigned32 (0..3)
MAX-ACCESS read-create
STATUS current
DESCRIPTION
"This is a status variable.
It is written by the SME when a measurement report is completed.
The HT Beamforming Calibration indicates that the STA can participate in a
calibration procedure initiated by another STA that is capable of generating
an immediate response Sounding PPDU and can provide a CSI report in
response to the receipt of a Sounding PPDU, equal to 0 if not supported,
equal to 1 is the STA can respond to a calibration request using the CSI
report but cannot initiate calibration, equal to 3 if the STA can both
initiate and respond to a calibration request. See 8.4.2.58.6"
::= { dot11RMNeighborReportEntry 56 }
dot11RMNeighborReportHTExplicitCSITransmitBeamformingCap OBJECT-TYPE
SYNTAX TruthValue
MAX-ACCESS read-create
STATUS current
DESCRIPTION
"This is a status variable.
It is written by the SME when a measurement report is completed.
The HT explicit CSI Transmit Beamforming capable indicates whether this
STA can apply transmit beamforming using SCI explicit feedback in its
transmission, equal to false if not supported, equal to true if supported.
See 8.4.2.58.6"
::= { dot11RMNeighborReportEntry 57 }
dot11RMNeighborReportHTExplicitNonCompressedSteeringCap OBJECT-TYPE
SYNTAX TruthValue
MAX-ACCESS read-create
STATUS current
DESCRIPTION
"This is a status variable.
It is written by the SME when a measurement report is completed.
The HT explicit noncompressed steering capable indicates whether this STA
can apply transmit beamforming using noncompressed beamforming feedback
matrix explicit feedback in its transmission, equal to false if not supported,
equal to true if supported. See 8.4.2.58.6"
::= { dot11RMNeighborReportEntry 58 }
dot11RMNeighborReportHTExplicitCompressedSteeringCap OBJECT-TYPE
SYNTAX TruthValue
MAX-ACCESS read-create
STATUS current
DESCRIPTION
"This is a status variable.
It is written by the SME when a measurement report is completed.
The HT explicit compressed steering capable indicates whether this STA can
apply transmit beamforming using compressed beamforming feedback matrix
explicit feedback in its transmission, equal to false if not supported,
equal to true if supported. See 8.4.2.58.6"
::= { dot11RMNeighborReportEntry 59}
dot11RMNeighborReportHTExplicitTransmitBeamformingFeedback OBJECT-TYPE
SYNTAX Unsigned32 (0..3)
MAX-ACCESS read-create
STATUS current
DESCRIPTION
"This is a status variable.
It is written by the SME when a measurement report is completed.
The HT explicit Transmit Beamforming CSI feedback indicates whether this
receiver can return CSI explicit feedback, equal to 0 if not supported,
equal to 1 for delayed feedback, equal to 2 for immediate feedback, equal
to 3 for delayed and immediate feedback. See 8.4.2.58.6"
::= { dot11RMNeighborReportEntry 60 }
dot11RMNbRprtHTExplicitNonCompressedBeamformingFeedbackCap OBJECT-TYPE
SYNTAX Unsigned32 (0..3)
MAX-ACCESS read-create
STATUS current
DESCRIPTION
"This is a status variable.
It is written by the SME when a measurement report is completed.
The HT Explicit noncompressed beamforming feedback capable indicates
whether this receiver can return noncompressed beamforming feedback matrix
explicit feedback, equal to 0 if not supported, equal to 1 for delayed
feedback, equal to 2 for immediate feedback, equal to 3 for delayed and
immediate feedback. See 8.4.2.58.6"
::= { dot11RMNeighborReportEntry 61 }
dot11RMNeighborReportHTExplicitCompressedBeamformingFeedbackCap OBJECT-TYPE
SYNTAX Unsigned32 (0..3)
MAX-ACCESS read-create
STATUS current
DESCRIPTION
"This is a status variable.
It is written by the SME when a measurement report is completed.
The HT explicit compressed beamforming feedback capable indicates whether
this receiver can return compressed beamforming feedback matrix explicit
feedback, equal to 0 if not supported, equal to 1 for delayed feedback,
equal to 2 for immediate feedback, equal to 3 for delayed and immediate
feedback. See 8.4.2.58.6"
::= { dot11RMNeighborReportEntry 62 }
dot11RMNeighborReportHTTransmitBeamformingMinimalGrouping OBJECT-TYPE
SYNTAX Unsigned32 (0..3)
MAX-ACCESS read-create
STATUS current
DESCRIPTION
"This is a status variable.
It is written by the SME when a measurement report is completed.
The HT Transmit Beamforming minimal grouping indicates the minimal grouping
used for explicit feedback reports, equal to 0 if the STA supports
groups of 1 (no grouping), equal to 1 to indicate groups of 1, 2, equal to
2 to indicate groups of 1, 4, equal to 3 to indicate groups of 1, 2, 4. See
8.4.2.58.6"
::= { dot11RMNeighborReportEntry 63 }
dot11RMNbRprtHTCSINumberofTxBeamformingAntennasSuppt OBJECT-TYPE
SYNTAX Unsigned32 (0..3)
MAX-ACCESS read-create
STATUS current
DESCRIPTION
"This is a status variable.
It is written by the SME when a measurement report is completed.
The HT CSI number of beamformer antennas supported indicates the maximum
number of beamformer antennas the beamformee can support when CSI feedback
is required, equal to 0 for single Tx antenna sounding, equal to 1 for 2
Tx antenna sounding, equal to 2 for 3 Tx antenna sounding, equal to 3 for
4 Tx antenna sounding. See 8.4.2.58.6"
::= { dot11RMNeighborReportEntry 64 }
dot11RMNbRprtHTNonCompressedSteeringNumofTxBmfmingAntennasSuppt OBJECT-TYPE
SYNTAX Unsigned32 (0..3)
MAX-ACCESS read-create
STATUS current
DESCRIPTION
"This is a status variable.
It is written by the SME when a measurement report is completed.
The HT noncompressed steering number of beamformer antennas supported
indicates the maximum number of beamformer antennas the beamformee can
support when noncompressed beamforming feedback matrix is required, equal
to 0 for single Tx antenna sounding, equal to 1 for 2 Tx antenna sounding,
equal to 2 for 3 Tx antenna sounding, equal to 3 for 4 Tx antenna sounding.
See 8.4.2.58.6"
::= { dot11RMNeighborReportEntry 65 }
dot11RMNbRprtHTCompressedSteeringNumberofTxBmfmingAntennasSuppt OBJECT-TYPE
SYNTAX Unsigned32 (0..3)
MAX-ACCESS read-create
STATUS current
DESCRIPTION
"This is a status variable.
It is written by the SME when a measurement report is completed.
The HT compressed steering number of beamformer antennas supported indicates
the maximum number of beamformer antennas the beamformee can support
when compressed beamforming feedback matrix is required, equal to 0 for
single Tx antenna sounding, equal to 1 for 2 Tx antenna sounding, equal to
2 for 3 Tx antenna sounding, equal to 3 for 4 Tx antenna sounding. See
8.4.2.58.6"
::= { dot11RMNeighborReportEntry 66 }
dot11RMNbRprtHTCSIMaxNumberofRowsTxBeamformingSuppt OBJECT-TYPE
SYNTAX Unsigned32 (0..3)
MAX-ACCESS read-create
STATUS current
DESCRIPTION
"This is a status variable.
It is written by the SME when a measurement report is completed.
The HT CSI max number of rows beamformer supported indicates the maximum
number of rows of CSI explicit feedback from the beamformee or calibration
responder or transmit ASEL responder that a beamformer or calibration initiator
or transmit ASEL initiator can support when SCI feedback is
required, equal to 0 for a single row of CSI, equal to 1 for 2 rows of CSI,
equal to 2 for 3 rows of CSI, equal to 3 for 4 rows of CSI. See 8.4.2.58.6"
::= { dot11RMNeighborReportEntry 67 }
dot11RMNeighborReportHTTransmitBeamformingChannelEstimationCap OBJECT-TYPE
SYNTAX Unsigned32 (0..3)
MAX-ACCESS read-create
STATUS current
DESCRIPTION
"This is a status variable.
It is written by the SME when a measurement report is completed.
The HT channel estimation capability indicates the maximum number of
space-time streams for which channel dimensions can be simultaneously
estimated when receiving an NDP sounding PPDU or the extension portion of
the HT-LTFs in a staggered sounding PPDU. Equal to 0 for 1 space-time
stream, equal to 1 for 2 space-time streams, equal to 2 for 3 space-time
streams, equal to 3 for 4 space-time streams. See 8.4.2.58.6"
::= { dot11RMNeighborReportEntry 68 }
dot11RMNeighborReportHTAntSelectionCap OBJECT-TYPE
SYNTAX TruthValue
MAX-ACCESS read-create
STATUS current
DESCRIPTION
"This is a status variable.
It is written by the SME when a measurement report is completed.
The HT ASEL capable indicates whether this STA supports ASEL, equal to
false if not supported, equal to true if supported. See 8.4.2.58.7"
::= { dot11RMNeighborReportEntry 69}
dot11RMNeighborReportHTExplicitCSIFeedbackBasedTxASELCap OBJECT-TYPE
SYNTAX TruthValue
MAX-ACCESS read-create
STATUS current
DESCRIPTION
"This is a status variable.
It is written by the SME when a measurement report is completed.
The HT explicit CSI feedback based transmit ASEL capable indicates whether
this STA has transmit ASEL capability based on explicit CSI feedback,
equal to false if not supported, equal to true if supported. See
8.4.2.58.7"
::= { dot11RMNeighborReportEntry 70 }
dot11RMNeighborReportHTAntIndicesFeedbackBasedTxASELCap OBJECT-TYPE
SYNTAX TruthValue
MAX-ACCESS read-create
STATUS current
DESCRIPTION
"This is a status variable.
It is written by the SME when a measurement report is completed.
The HT antenna indices feedback based transmit ASEL capable indicates
whether this STA has transmit ASEL capability based on antenna indices
feedback, equal to false if not supported, equal to true if supported. See
8.4.2.58.7"
::= { dot11RMNeighborReportEntry 71 }
dot11RMNeighborReportHTExplicitCSIFeedbackBasedCap OBJECT-TYPE
SYNTAX TruthValue
MAX-ACCESS read-create
STATUS current
DESCRIPTION
"This is a status variable.
It is written by the SME when a measurement report is completed.
The explicit CSI feedback capable indicates whether this STA can compute
CSI and feedback in support of ASEL, equal to false if not supported,
equal to true is supported. See 8.4.2.58.7"
::= { dot11RMNeighborReportEntry 72 }
dot11RMNeighborReportHTAntIndicesFeedbackCap OBJECT-TYPE
SYNTAX TruthValue
MAX-ACCESS read-create
STATUS current
DESCRIPTION
"This is a status variable.
It is written by the SME when a measurement report is completed.
The HT antenna indices feedback capable indicates whether this STA has Rx
ASEL capability, equal to false if not supported, equal to true if supported.
See 8.4.2.58.7"
::= { dot11RMNeighborReportEntry 73 }
dot11RMNeighborReportHTRxASELCap OBJECT-TYPE
SYNTAX TruthValue
MAX-ACCESS read-create
STATUS current
DESCRIPTION
"This is a status variable.
It is written by the SME when a measurement report is completed.
The HT receive ASEL capable indicates whether this STA has Rx ASEL capability,
equal to false if not supported, equal to true if supported. See
8.4.2.58.7"
::= { dot11RMNeighborReportEntry 74 }
dot11RMNeighborReportHTTxSoundingPPDUsCap OBJECT-TYPE
SYNTAX TruthValue
MAX-ACCESS read-create
STATUS current
DESCRIPTION
"This is a status variable.
It is written by the SME when a measurement report is completed.
The HT transmit sounding PPDUs capable indicates whether this STA can
transmit sounding PPDUs for ASEL training per request, equal to false if
not supported, equal to true if supported. See 8.4.2.58.7"
::= { dot11RMNeighborReportEntry 75 }
dot11RMNeighborReportHTInfoPrimaryChannel OBJECT-TYPE
SYNTAX Unsigned32
MAX-ACCESS read-create
STATUS current
DESCRIPTION
"This is a status variable.
It is written by the SME when a measurement report is completed.
The HT Info primary channel indicates the channel number of the primary
channel, encoding: channel number of the primary channel. See 8.4.2.59"
::= { dot11RMNeighborReportEntry 76 }
dot11RMNeighborReportHTInfoSecChannelOffset OBJECT-TYPE
SYNTAX Unsigned32 (0..3)
MAX-ACCESS read-create
STATUS current
DESCRIPTION
"This is a status variable.
It is written by the SME when a measurement report is completed.
The HT Info secondary channel offset indicates the offset of the secondary
channel relative to the primary channel, equal to 1 if the secondary channel
is above the primary channel, equal to 3 if the secondary channel is
below the primary channel, equal to 0 if no secondary channel is present.
The value 2 is reserved. See 8.4.2.59"
::= { dot11RMNeighborReportEntry 77 }
dot11RMNeighborReportHTInfoSTAChannelWidth OBJECT-TYPE
SYNTAX TruthValue
MAX-ACCESS read-create
STATUS current
DESCRIPTION
"This is a status variable.
It is written by the SME when a measurement report is completed.
The HT Info STA channel width defines the channel widths that may be used
to transmit to the STA, equal to false for a 20 MHz channel width, equal
to true allows use of any channel width in the supported channel width
set. See 8.4.2.59"
::= { dot11RMNeighborReportEntry 78 }
dot11RMNeighborReportHTInfoRIFSMode OBJECT-TYPE
SYNTAX TruthValue
MAX-ACCESS read-create
STATUS current
DESCRIPTION
"This is a status variable.
It is written by the SME when a measurement report is completed.
The HT Info RIFS mode indicates whether use of RIFS is permitted within
the BSS, equal to false if use of RIFS is prohibited, equal to true if use
of RIFS is permitted. See 8.4.2.59"
::= { dot11RMNeighborReportEntry 79}
dot11RMNeighborReportHTInfoProtection OBJECT-TYPE
SYNTAX Unsigned32 (0..3)
MAX-ACCESS read-create
STATUS current
DESCRIPTION
"This is a status variable.
It is written by the SME when a measurement report is completed.
The HT Info protection indicates protection requirements of HT transmissions.
Equal to 0 if all STAs detected in the primary or the secondary
channel or that are a member of this BSS are HT STAs and either all STAs
that are known by the transmitting STA to be a member of this BSS are 20/
40 MHz HT in a 20/40 MHz BSS or this BSS is a 20 MHz BSS. Equal to 1 (nonmember
protection mode) if there is at least one non-HT STA detected in
either the primary or the secondary channel or in both the primary and
secondary channels and that is not known by the transmitting STA to be a
member of this BSS and all STAs that are known by the transmitting STA to
be a member of this BSS are HT STAs. Equal to 2 if all STAs detected in the
primary or the secondary channel or that are known by the transmitting STA
to be a member of this BSS are HT STAs and this BSS is a 20/40 MHz BSS and
there is at least one 20 MHz HT STA associated with this BSS. Equal to 3
(non-HT mixed mode) otherwise. See 8.4.2.58.2"
::= { dot11RMNeighborReportEntry 80 }
dot11RMNeighborReportHTInfoNonGreenfieldHTSTAsPresent OBJECT-TYPE
SYNTAX TruthValue
MAX-ACCESS read-create
STATUS current
DESCRIPTION
"This is a status variable.
It is written by the SME when a measurement report is completed.
The HT Info nongreenfield HT STAs present indicates if any HT STAs that
are not HT-greenfield capable have associated. Determines when a non-AP
STA should use HT-greenfield protection. Present in Beacon and Probe
Response frames transmitted by an AP. Equal to false if all HT STAs that
are associated are HT-greenfield capable, equal to true if one or more HT
STAs that are not HT-greenfield capable are associated. See 8.4.2.59"
::= { dot11RMNeighborReportEntry 81 }
dot11RMNeighborReportHTInfoOBSSNonHTSTAsPresent OBJECT-TYPE
SYNTAX TruthValue
MAX-ACCESS read-create
STATUS current
DESCRIPTION
"This is a status variable.
It is written by the SME when a measurement report is completed.
The HT Info OBSS non-HT STAs present indicates if the use of protection
for non-HT STAs by OBSSs is determined to be desirable. Present in Beacon
and Probe Response frames transmitted by an AP, equal to true if the use
of protection for non-HT STAs by OBSSs is determined to be desirable,
equal to false otherwise. See 8.4.2.59"
::= { dot11RMNeighborReportEntry 82 }
dot11RMNeighborReportHTInfoDualBeacon OBJECT-TYPE
SYNTAX TruthValue
MAX-ACCESS read-create
STATUS current
DESCRIPTION
"This is a status variable.
It is written by the SME when a measurement report is completed.
The HT Info dual beacon indicates whether the AP transmits an STBC beacon,
equal to false if no STBC beacon is transmitted, equal to true if an STBC
beacon is transmitted. See 8.4.2.59"
::= { dot11RMNeighborReportEntry 83 }
dot11RMNeighborReportHTInfoDualCTSProtection OBJECT-TYPE
SYNTAX TruthValue
MAX-ACCESS read-create
STATUS current
DESCRIPTION
"This is a status variable.
It is written by the SME when a measurement report is completed.
The HT Info dual CTS protection is used by the AP to set a NAV at STAs that
do not support STBC and at STAs that can associate solely through the secondary
beacon, equal to false if dual CTS protection is not required,
equal to true if dual CTS protection is required. See 8.4.2.59"
::= { dot11RMNeighborReportEntry 84 }
dot11RMNeighborReportHTInfoSTBCBeacon OBJECT-TYPE
SYNTAX TruthValue
MAX-ACCESS read-create
STATUS current
DESCRIPTION
"This is a status variable.
It is written by the SME when a measurement report is completed.
The HT Info STBC beacon indicates whether the beacon containing this element
is a primary or a STBC beacon, equal to false in a primary beacon,
equal to true in a STBC beacon. See 8.4.2.59"
::= { dot11RMNeighborReportEntry 85 }
dot11RMNeighborReportHTInfoLSIGTXOPProtectionSup OBJECT-TYPE
SYNTAX TruthValue
MAX-ACCESS read-create
STATUS current
DESCRIPTION
"This is a status variable.
It is written by the SME when a measurement report is completed.
The HT Info L-SIG TXOP protection full support indicates whether all HT
STA in the BSS support L-SIG TXOP protection, equal to false if one or
more HT STA in the BSS do not support L-SIG TXOP protection, equal to true
if all HT STA in the BSS support L-SIG TXOP protection. See 8.4.2.59"
::= { dot11RMNeighborReportEntry 86 }
dot11RMNeighborReportHTInfoPCOActive OBJECT-TYPE
SYNTAX TruthValue
MAX-ACCESS read-create
STATUS current
DESCRIPTION
"This is a status variable.
It is written by the SME when a measurement report is completed.
The HT Info PCO active indicates whether PCO is active in the BSS, equal
to false if PCO is not active in the BSS, equal to true if PCO is active
in the BSS. See 8.4.2.59"
::= { dot11RMNeighborReportEntry 87}
dot11RMNeighborReportHTInfoPCOPhase OBJECT-TYPE
SYNTAX TruthValue
MAX-ACCESS read-create
STATUS current
DESCRIPTION
"This is a status variable.
It is written by the SME when a measurement report is completed.
The HT Info PCO phase indicates the PCO phase of operation, equal to false
indicates a switch to or continued 20 MHz phase, equal to true indicates a
switch to or continuation of 40 MHz phase. See 8.4.2.59"
::= { dot11RMNeighborReportEntry 88 }
dot11RMNeighborReportHTInfoBasicMCSSet OBJECT-TYPE
SYNTAX OCTET STRING (SIZE(16))
MAX-ACCESS read-create
STATUS current
DESCRIPTION
"This is a status variable.
It is written by the SME when a measurement report is completed.
The HT Info Basic MCS Set indicates values that are supported by all HT
STAs in the BSS. The Basic MCS Set is a bitmap of size 128 bits. Bit 0 corresponds
to MCS 0. A bit is equal to 1 to indicate support for that MCS,
equal to 0 otherwise. See 8.4.2.59"
::= { dot11RMNeighborReportEntry 89 }
dot11RMNeighborReportHTSecChannelOffset OBJECT-TYPE
SYNTAX Unsigned32 (0..3)
MAX-ACCESS read-create
STATUS current
DESCRIPTION
"This is a status variable.
It is written by the SME when a measurement report is completed.
The HT secondary channel offset indicates the position of the secondary
channel relative to the primary channel, equal to 1 to indicate that the
secondary channel is above the primary channel, equal to 3 to indicate the
secondary channel is below the primary channel, equal to 0 to indicate
that no secondary channel is present. The value 2 is reserved. See
8.4.2.22"
::= { dot11RMNeighborReportEntry 90 }
dot11RMNeighborReportExtCapPSMPSupport OBJECT-TYPE
SYNTAX TruthValue
MAX-ACCESS read-create
STATUS current
DESCRIPTION
"This is a status variable.
It is written by the SME when a measurement report is completed.
The Extended Capabilities PSMP support indicates support for PSMP operation,
equal to false if PSMP is not supported, equal to true if PSMP operation
is supported. See 8.4.2.29"
::= { dot11RMNeighborReportEntry 91 }
dot11RMNeighborReportExtCapSPSMPSup OBJECT-TYPE
SYNTAX TruthValue
MAX-ACCESS read-create
STATUS current
DESCRIPTION
"This is a status variable.
It is written by the SME when a measurement report is completed.
The HT Info S-PSMP support indicates support for scheduled PSMP, equal to
false when PSMP is supported is equal to false and when PSMP support is
equal to 1 if the STA does not support S-PSMP, equal to true when PSMP
support is equal to 1 if the STA supports S-PSMP. See 8.4.2.29"
::= { dot11RMNeighborReportEntry 92 }
dot11RMNeighborReportExtCapServiceIntervalGranularity OBJECT-TYPE
SYNTAX Unsigned32 (0..7)
MAX-ACCESS read-create
STATUS current
DESCRIPTION
"This is a status variable.
It is written by the SME when a measurement report is completed.
The Extended Capabilities SI granularity indicates the duration of the
shortest SI, equal to 0 for 5 ms, equal to 1 for 10 ms, equal to 2 for 15
ms, equal to 3 for 20 ms, equal to 4 for 25 ms, equal to 5 for 30 ms, equal
to 6 for 35 ms, equal to 7 for 40 ms. See 8.4.2.29"
::= { dot11RMNeighborReportEntry 93 }
dot11RMNeighborReportBSSTransitCandPreference OBJECT-TYPE
SYNTAX Unsigned32 (0..255)
MAX-ACCESS read-create
STATUS current
DESCRIPTION
"This attribute indicates the network preference for BSS transition to the
BSS listed in this BSS Transition Candidate List Entries field in the BSS
Transition Management Request frame, BSS Transition Management Query frame
and BSS Transition Management Response frame. The Preference field value
is a number ranging from 0 to 255 indicating an ordering of preferences
for the BSS transition candidates for this STA. The value 0 indicates an
excluded BSS. The values 1-255 the preferred relative ordering of BSSs,
with 255 indicating the most preferred candidate and 1 indicating the
least preferred candidate. Additional details describing use of the Preference
field are provided in 10.23.6.3."
::= { dot11RMNeighborReportEntry 94 }
dot11RMNeighborReportBSSTerminationTSF OBJECT-TYPE
SYNTAX TSFType
MAX-ACCESS read-create
STATUS current
DESCRIPTION
"This attribute indicates the value of the TSF counter when the BSS termination
will occur in the future. A BSS Termination TSF field value of 0
indicates that termination of the BSS will occur imminently. Prior to termination
of the BSS, all associated STAs are disassociated by the AP."
::= { dot11RMNeighborReportEntry 95 }
dot11RMNeighborReportBSSTerminationDuration OBJECT-TYPE
SYNTAX Unsigned32 (1..65535)
UNITS "minutes"
MAX-ACCESS read-create
STATUS current
DESCRIPTION
"This attribute indicates the number of minutes for which the BSS is not
present. The Duration field value of 0 is reserved. The Duration field
value is set to 65 535 when the BSS is terminated for a period longer than
or equal to 65 535 minutes."
::= { dot11RMNeighborReportEntry 96 }
-- ********************************************************************
-- * End of dot11RMNeighborReport TABLE
-- ********************************************************************
-- ********************************************************************
-- * END of Radio Measurement Interface MIB
-- ********************************************************************
-- ********************************************************************
-- * dot11FastBSSTransitionConfig TABLE
-- ********************************************************************
dot11FastBSSTransitionConfigTable OBJECT-TYPE
SYNTAX SEQUENCE OF Dot11FastBSSTransitionConfigEntry
MAX-ACCESS not-accessible
STATUS current
DESCRIPTION
"The table containing fast BSS transition configuration objects."
::= { dot11smt 15 }
dot11FastBSSTransitionConfigEntry OBJECT-TYPE
SYNTAX Dot11FastBSSTransitionConfigEntry
MAX-ACCESS not-accessible
STATUS current
DESCRIPTION
"An entry in the dot11FastBSSTransitionConfigTable."
INDEX { ifIndex }
::= { dot11FastBSSTransitionConfigTable 1 }
Dot11FastBSSTransitionConfigEntry ::=
SEQUENCE {
dot11FastBSSTransitionActivated TruthValue,
dot11FTMobilityDomainID OCTET STRING,
dot11FTOverDSActivated TruthValue,
dot11FTResourceRequestSupported TruthValue,
dot11FTR0KeyHolderID OCTET STRING,
dot11FTR0KeyLifetime Unsigned32,
dot11FTR1KeyHolderID OCTET STRING,
dot11FTReassociationDeadline Unsigned32 }
dot11FastBSSTransitionActivated OBJECT-TYPE
SYNTAX TruthValue
MAX-ACCESS read-write
STATUS current
DESCRIPTION
"This is a control variable.
It is written by an external management entity.
Changes take effect as soon as practical in the implementation.
When this object is true, this indicates that fast BSS transition (FT) is
enabled on this entity. The entity advertises the FT-related elements in
its Beacon and Probe Response frames. This object requires that
dot11FastBSSTransitionImplemented also be equal to true."
::= { dot11FastBSSTransitionConfigEntry 1 }
dot11FTMobilityDomainID OBJECT-TYPE
SYNTAX OCTET STRING (SIZE(2))
MAX-ACCESS read-write
STATUS current
DESCRIPTION
"This is a control variable.
It is written by an external management entity.
Changes take effect as soon as practical in the implementation.
This attribute specifies the Mobility Domain identifier (MDID) of this
entity.
The MDID is used to indicate a group of APs, within an ESS, between which
a STA can use fast BSS transition services. Fast BSS transitions are
allowed only between APs that have the same MDID and are within the same
ESS. They are not allowed between APs with different MDIDs or in different
ESSs.
Since fast BSS transition services are defined only within the scope of an
ESS, there is no requirement that MDIDs be unique across ESSs."
::= { dot11FastBSSTransitionConfigEntry 2 }
dot11FTOverDSActivated OBJECT-TYPE
SYNTAX TruthValue
MAX-ACCESS read-write
STATUS current
DESCRIPTION
"This is a control variable.
It is written by an external management entity.
Changes take effect as soon as practical in the implementation.
When this object is true, this indicates that fast BSS transition via the
over-the-DS protocol as described in Clause 12 is enabled on this AP
entity."
::= { dot11FastBSSTransitionConfigEntry 3 }
dot11FTResourceRequestSupported OBJECT-TYPE
SYNTAX TruthValue
MAX-ACCESS read-write
STATUS current
DESCRIPTION
"This is a control variable.
It is written by an external management entity.
Changes take effect as soon as practical in the implementation.
When this object is true, this indicates that the fast BSS transition (FT)
resource request procedures of 12.10 are supported on this AP entity."
::= { dot11FastBSSTransitionConfigEntry 4 }
dot11FTR0KeyHolderID OBJECT-TYPE
SYNTAX OCTET STRING (SIZE(1..48))
MAX-ACCESS read-write
STATUS current
DESCRIPTION
"This is a control variable.
It is written by an external management entity.
Changes take effect as soon as practical in the implementation.
This attribute specifies the PMK-R0 key holder identifier (R0KH-ID) of the
Authenticator of this AP.
NOTE: Backend protocol may allow longer NAS Client identifiers (e.g.,
RADIUS allows up to 253-octet NAS-Identifier), but when used with fast BSS
transition, the maximum length is limited to 48 octets. The same value
must be used for the NAS Client identifier and dot11FTR0KeyHolderID."
::= { dot11FastBSSTransitionConfigEntry 5 }
dot11FTR0KeyLifetime OBJECT-TYPE
SYNTAX Unsigned32 (60..4294967295)
MAX-ACCESS read-write
STATUS current
DESCRIPTION
"This is a control variable.
It is written by an external management entity.
Changes take effect as soon as practical in the implementation.
This attribute specifies the default lifetime of the PMK-R0, in seconds,
when a Session-Timeout attribute is not provided during the EAP authentication.
This attribute also applies when the PMK-R0 is derived from a
PSK."
DEFVAL { 1209600 }
::= { dot11FastBSSTransitionConfigEntry 6 }
dot11FTR1KeyHolderID OBJECT-TYPE
SYNTAX OCTET STRING (SIZE(6))
MAX-ACCESS read-write
STATUS current
DESCRIPTION
"This is a control variable.
It is written by an external management entity.
Changes take effect as soon as practical in the implementation.
This attribute specifies the PMK-R1 key holder identifier (R1KH-ID) of the
Authenticator of this AP. It is equal to a MAC address of the entity holding
the PMK-R1 in the Authenticator."
::= { dot11FastBSSTransitionConfigEntry 7 }
dot11FTReassociationDeadline OBJECT-TYPE
SYNTAX Unsigned32 (1000..4294967295)
MAX-ACCESS read-write
STATUS current
DESCRIPTION
"This is a control variable.
It is written by an external management entity.
Changes take effect as soon as practical in the implementation.
This attribute specifies the number of time units (TUs) that this target
AP entity retains a PTKSA and reserves any specified resources for a STA
while waiting for a reassociation from that STA. It is assumed that this
value is administered consistently across the mobility domain."
DEFVAL { 1000 }
::= { dot11FastBSSTransitionConfigEntry 8 }
-- *********************************************************************
-- * End of dot11FastBSSTransitionConfig TABLE
-- *********************************************************************
-- ********************************************************************
-- * dot11LCIDSE TABLE
-- ********************************************************************
dot11LCIDSETable OBJECT-TYPE
SYNTAX SEQUENCE OF Dot11LCIDSEEntry
MAX-ACCESS not-accessible
STATUS current
DESCRIPTION
"Group contains conceptual table of attributes for Dependent Station
Enablement."
::= { dot11smt 16 }
dot11LCIDSEEntry OBJECT-TYPE
SYNTAX Dot11LCIDSEEntry
MAX-ACCESS not-accessible
STATUS current
DESCRIPTION
"An entry in the dot11LCIDSETable Indexed by dot11LCIDSEIndex."
INDEX { dot11LCIDSEIndex }
::= { dot11LCIDSETable 1 }
Dot11LCIDSEEntry ::=
SEQUENCE {
dot11LCIDSEIndex Unsigned32,
dot11LCIDSEIfIndex InterfaceIndex,
dot11LCIDSECurrentOperatingClass Unsigned32,
dot11LCIDSELatitudeResolution Unsigned32,
dot11LCIDSELatitudeInteger Integer32,
dot11LCIDSELatitudeFraction Integer32,
dot11LCIDSELongitudeResolution Unsigned32,
dot11LCIDSELongitudeInteger Integer32,
dot11LCIDSELongitudeFraction Integer32,
dot11LCIDSEAltitudeType INTEGER,
dot11LCIDSEAltitudeResolution Unsigned32,
dot11LCIDSEAltitudeInteger Integer32,
dot11LCIDSEAltitudeFraction Integer32,
dot11LCIDSEDatum Unsigned32,
dot11RegLocAgreement TruthValue,
dot11RegLocDSE TruthValue,
dot11DependentSTA TruthValue,
dot11DependentEnablementIdentifier Unsigned32,
dot11DSEEnablementTimeLimit Unsigned32,
dot11DSEEnablementFailHoldTime Unsigned32,
dot11DSERenewalTime Unsigned32,
dot11DSETransmitDivisor Unsigned32 }
dot11LCIDSEIndex OBJECT-TYPE
SYNTAX Unsigned32
MAX-ACCESS not-accessible
STATUS current
DESCRIPTION
"Index for LCI DSE elements in dot11LCIDSETable, greater than 0."
::= { dot11LCIDSEEntry 1 }
dot11LCIDSEIfIndex OBJECT-TYPE
SYNTAX InterfaceIndex
MAX-ACCESS read-only
STATUS current
DESCRIPTION
"Each IEEE 802.11 interface is represented by an ifEntry. Interface Tables
in this MIB are indexed by ifIndex."
::= { dot11LCIDSEEntry 2 }
dot11LCIDSECurrentOperatingClass OBJECT-TYPE
SYNTAX Unsigned32 (0..255)
MAX-ACCESS read-only
STATUS current
DESCRIPTION
"This is a control variable.
It is written by the SME when the device is initialized.
Current Operating Class is 8 bits indicating the particular Operating
Class in use by the radio."
::= { dot11LCIDSEEntry 3 }
dot11LCIDSELatitudeResolution OBJECT-TYPE
SYNTAX Unsigned32 (0..63)
MAX-ACCESS read-only
STATUS current
DESCRIPTION
"This is a control variable.
It is written by the SME when the device is initialized.
Latitude resolution is 6 bits indicating the number of valid bits in the
fixed-point value of Latitude. This field is derived from IETF RFC 3825."
::= { dot11LCIDSEEntry 4 }
dot11LCIDSELatitudeInteger OBJECT-TYPE
SYNTAX Integer32 (-359..359)
MAX-ACCESS read-only
STATUS current
DESCRIPTION
"This is a control variable.
It is written by the SME when the device is initialized.
Latitude is a twos-complement 34-bit fixed point value consisting of 9
bits of integer and 25 bits of fraction. This field contains the 9 bits of
integer portion of Latitude. This field is derived from IETF RFC 3825."
::= { dot11LCIDSEEntry 5 }
dot11LCIDSELatitudeFraction OBJECT-TYPE
SYNTAX Integer32 (-16777215..16777215)
MAX-ACCESS read-only
STATUS current
DESCRIPTION
"This is a control variable.
It is written by the SME when the device is initialized.
Latitude is a twos-complement 34-bit fixed point value consisting of 9
bits of integer and 25 bits of fraction. This field contains the 25 bits
of fraction portion of Latitude. This field is derived from IETF RFC
3825."
::= { dot11LCIDSEEntry 6 }
dot11LCIDSELongitudeResolution OBJECT-TYPE
SYNTAX Unsigned32 (0..63)
MAX-ACCESS read-only
STATUS current
DESCRIPTION
"This is a control variable.
It is written by the SME when the device is initialized.
Longitude resolution is 6 bits indicating the number of valid bits in the
fixed-point value of Longitude. This field is derived from IETF RFC 3825."
::= { dot11LCIDSEEntry 7 }
dot11LCIDSELongitudeInteger OBJECT-TYPE
SYNTAX Integer32 (-359..359)
MAX-ACCESS read-only
STATUS current
DESCRIPTION
"This is a control variable.
It is written by the SME when the device is initialized.
Longitude is a twos-complement 34-bit fixed point value consisting of 9
bits of integer and 25 bits of fraction. This field contains the 9 bits of
integer portion of Longitude. This field is derived from IETF RFC 3825."
::= { dot11LCIDSEEntry 8 }
dot11LCIDSELongitudeFraction OBJECT-TYPE
SYNTAX Integer32 (-16777215..16777215)
MAX-ACCESS read-only
STATUS current
DESCRIPTION
"This is a control variable.
It is written by the SME when the device is initialized.
Longitude is a twos-complement 34-bit fixed point value consisting of 9
bits of integer and 25 bits of fraction. This field contains the 25 bits
of fraction portion of Longitude. This field is derived from IETF RFC
3825."
::= { dot11LCIDSEEntry 9 }
dot11LCIDSEAltitudeType OBJECT-TYPE
SYNTAX INTEGER { meters(1), floors(2), hagm(3) }
MAX-ACCESS read-only
STATUS current
DESCRIPTION
"This is a control variable.
It is written by the SME when the device is initialized.
Altitude Type is 4 bits encoding the type of altitude.
Codes defined are:
meters : in 2s-complement fixed-point 22-bit integer part with 8-bit fraction
floors : in 2s-complement fixed-point 22-bit integer part with 8-bit fraction
hagm : Height Above Ground in meters, in 2s-complement fixed-point 22-bit
integer part with 8-bit fraction.
This field is derived from IETF RFC 3825."
DEFVAL { 3 }
::= { dot11LCIDSEEntry 10 }
dot11LCIDSEAltitudeResolution OBJECT-TYPE
SYNTAX Unsigned32 (0..63)
MAX-ACCESS read-only
STATUS current
DESCRIPTION
"This is a control variable.
It is written by the SME when the device is initialized.
Altitude resolution is 6 bits indicating the number of valid bits in the
altitude. This field is derived from IETF RFC 3825."
::= { dot11LCIDSEEntry 11 }
dot11LCIDSEAltitudeInteger OBJECT-TYPE
SYNTAX Integer32 (-2097151..2097151)
MAX-ACCESS read-only
STATUS current
DESCRIPTION
"This is a control variable.
It is written by the SME when the device is initialized.
Altitude is a 30-bit value defined by the Altitude type field. The field
is encoded as a 2s-complement fixed-point 22-bit integer Part with 8-bit
fraction. This field contains the fixed-point Part of Altitude. This field
is derived from IETF RFC 3825."
::= { dot11LCIDSEEntry 12 }
dot11LCIDSEAltitudeFraction OBJECT-TYPE
SYNTAX Integer32 (-127..127)
MAX-ACCESS read-only
STATUS current
DESCRIPTION
"This is a control variable.
It is written by the SME when the device is initialized.
Altitude is a 30-bit value defined by the Altitude type field. The field
is encoded as a 2s-complement fixed-point 22-bit integer Part with 8-bit
fraction. This field contains the fraction part of Altitude. This field is
derived from IETF RFC 3825."
::= { dot11LCIDSEEntry 13 }
dot11LCIDSEDatum OBJECT-TYPE
SYNTAX Unsigned32 (1..3)
MAX-ACCESS read-only
STATUS current
DESCRIPTION
"This is a control variable.
It is written by the SME when the device is initialized.
Datum is an 8-bit value encoding the horizontal and vertical references
used for the coordinates given in this LCI. IETF RFC 3825 defines the values
of Datum. Type 1 is WGS-84, the coordinate system used by GPS. Type 2
is NAD83 with NAVD88 vertical reference. Type 3 is NAD83 with Mean Lower
Low Water vertical datum. All other types are reserved. This field is
derived from IETF RFC 3825."
DEFVAL { 1 }
::= { dot11LCIDSEEntry 14 }
dot11RegLocAgreement OBJECT-TYPE
SYNTAX TruthValue
MAX-ACCESS read-only
STATUS current
DESCRIPTION
"This is a status variable.
It is written by the MAC when a DSE Enablement frame is received.
RegLocAgreement reports the Enabling STA's Agreement status. False indicates
it is operating away from national borders and outside national policy
zones. True indicates it is operating by agreement near national
borders or inside national policy zones."
DEFVAL { false }
::= { dot11LCIDSEEntry 15 }
dot11RegLocDSE OBJECT-TYPE
SYNTAX TruthValue
MAX-ACCESS read-only
STATUS current
DESCRIPTION
"This is a status variable.
It is written by the MAC when a DSE Enablement frame is received.
RegLocDSE reports the Enabling STA's DSE status. False indicates Dependent
STAs are not enabled. True indicates Dependent STA operation is enabled."
DEFVAL { false }
::= { dot11LCIDSEEntry 16 }
dot11DependentSTA OBJECT-TYPE
SYNTAX TruthValue
MAX-ACCESS read-only
STATUS current
DESCRIPTION
"This is a status variable.
It is written by the MAC when a DSE Enablement frame is received.
This attribute reports the Dependent STA status of the STA that sent the
beacon or Probe Response with this information. False indicates that STA
is not operating as a Dependent STA. True indicates that STA is operating
as a Dependent STA."
DEFVAL { true }
::= { dot11LCIDSEEntry 17 }
dot11DependentEnablementIdentifier OBJECT-TYPE
SYNTAX Unsigned32 (0..65535)
MAX-ACCESS read-only
STATUS current
DESCRIPTION
"This is a status variable.
It is written by the MAC when a DSE Enablement frame is received.
This attribute reports the Dependent STA identifier assigned by the
enabling STA to the dependent station."
DEFVAL { 0 }
::= { dot11LCIDSEEntry 18 }
dot11DSEEnablementTimeLimit OBJECT-TYPE
SYNTAX Unsigned32
MAX-ACCESS read-only
STATUS current
DESCRIPTION
"This is a control variable.
It is written by the SME when the device is initialized.
dot11DSEAssociateTimeLimit indicates the maximum number of seconds that a
dependent STA may transmit in a DSE frequency band while attaining enablement
with an enabling STA. Unless another value is mandated by regulatory
authorities, the value is 32 seconds."
DEFVAL { 32 }
::= { dot11LCIDSEEntry 19 }
dot11DSEEnablementFailHoldTime OBJECT-TYPE
SYNTAX Unsigned32
MAX-ACCESS read-only
STATUS current
DESCRIPTION
"This is a control variable.
It is written by the SME when the device is initialized.
dot11DSEAssociateFailHoldTime indicates the number of seconds that a
dependent STA must not transmit in a DSE frequency band when it fails to
attain enablement with an enabling STA within dot11DSEEnablementTimeLimit
seconds. Unless another value is mandated by regulatory authorities, the
value is 512 seconds."
DEFVAL { 512 }
::= { dot11LCIDSEEntry 20}
dot11DSERenewalTime OBJECT-TYPE
SYNTAX Unsigned32
MAX-ACCESS read-only
STATUS current
DESCRIPTION
"This is a control variable.
It is written by the SME when the device is initialized.
dot11DSERenewalTime indicates the maximum number of seconds that a dependent
STA may operate in a DSE frequency band without receiving and decoding
an enabling signal from its enabling STA. Unless another value is
mandated by regulatory authorities, the value is 60 seconds."
DEFVAL { 60 }
::= { dot11LCIDSEEntry 21}
dot11DSETransmitDivisor OBJECT-TYPE
SYNTAX Unsigned32
MAX-ACCESS read-only
STATUS current
DESCRIPTION
"This is a control variable.
It is written by the SME when the device is initialized.
dot11DSETransmitDivisor indicates the value used by a dependent STA when
operating in a DSE frequency band and transmitting. The dependent STA
sends an Action frame when the sum of dot11TransmittedFragmentCount,
dot11GroupTransmittedFrameCount and dot11ReceivedFragmentCount modulo
dot11DSETransmitDivisor equals 0. Unless another value is mandated by regulatory
authorities, the default value is 256."
DEFVAL { 256 }
::= { dot11LCIDSEEntry 22}
-- ********************************************************************
-- * End of dot11LCIDSE TABLE
-- ********************************************************************
-- **********************************************************************
-- * dot11HTStationConfig TABLE
-- **********************************************************************
dot11HTStationConfigTable OBJECT-TYPE
SYNTAX SEQUENCE OF Dot11HTStationConfigEntry
MAX-ACCESS not-accessible
STATUS current
DESCRIPTION
"Station Configuration attributes. In tabular form to allow for multiple
instances on an agent."
::= { dot11smt 17 }
dot11HTStationConfigEntry OBJECT-TYPE
SYNTAX Dot11HTStationConfigEntry
MAX-ACCESS not-accessible
STATUS current
DESCRIPTION
"An entry (conceptual row) in the dot11HTStationConfig Table.
ifIndex - Each IEEE 802.11 interface is represented by an ifEntry. Interface
tables in this MIB module are indexed by ifIndex."
INDEX { ifIndex }
::= { dot11HTStationConfigTable 1 }
Dot11HTStationConfigEntry ::=
SEQUENCE {
dot11HTOperationalMCSSet OCTET STRING,
dot11MIMOPowerSave INTEGER,
dot11NDelayedBlockAckOptionImplemented TruthValue,
dot11MaxAMSDULength INTEGER,
dot11STBCControlFrameOptionImplemented TruthValue,
dot11LsigTxopProtectionOptionImplemented TruthValue,
dot11MaxRxAMPDUFactor Unsigned32,
dot11MinimumMPDUStartSpacing Unsigned32,
dot11PCOOptionImplemented TruthValue,
dot11TransitionTime Unsigned32,
dot11MCSFeedbackOptionImplemented INTEGER,
dot11HTControlFieldSupported TruthValue,
dot11RDResponderOptionImplemented TruthValue,
dot11SPPAMSDUCapable TruthValue,
dot11SPPAMSDURequired TruthValue,
dot11FortyMHzOptionImplemented TruthValue }
dot11HTOperationalMCSSet OBJECT-TYPE
SYNTAX OCTET STRING (SIZE(1..127))
MAX-ACCESS read-write
STATUS current
DESCRIPTION
"This is a control variable.
It is written by an external management entity.
Changes take effect for the next MLME-START.request primitive or MLMEJOIN.
request primitive.
This attribute shall specify the set of MCS at which the station may
transmit data. Each octet contains a value representing a rate. Each MCS
shall be within the range from 1 to 127, and shall be supported for
receiving data. This value is reported in transmitted Beacon, Probe
Request, Probe Response, Association Request, Association Response, 
Reas sociation Request, and Reassociation Response frames, and is used to
determine whether a BSS with which the station desires to synchronize is
suitable. It is also used when starting a BSS, as specified in 10.3."
::= { dot11HTStationConfigEntry 1 }
dot11MIMOPowerSave OBJECT-TYPE
SYNTAX INTEGER { static(1), dynamic(2), mimo(3) }
MAX-ACCESS read-only
STATUS current
DESCRIPTION
"This is a status variable.
It is written by the PHY when the power save condition changes.
This is an 8-bit integer value that identifies the configured power save
state of MIMO."
::= { dot11HTStationConfigEntry 2 }
dot11NDelayedBlockAckOptionImplemented OBJECT-TYPE
SYNTAX TruthValue
MAX-ACCESS read-only
STATUS current
DESCRIPTION
"This is a capability variable.
Its value is determined by device capabilities.
This attribute, when true, indicates that the station implementation is
capable of supporting the No Ack option of the Delayed Block Ack."
DEFVAL { false }
::= { dot11HTStationConfigEntry 3 }
dot11MaxAMSDULength OBJECT-TYPE
SYNTAX INTEGER { short(3839), long(7935) }
MAX-ACCESS read-only
STATUS current
DESCRIPTION
"This is a capability variable.
Its value is determined by device capabilities.
This attribute indicates the supported maximum size of A-MSDU."
DEFVAL { short }
::= { dot11HTStationConfigEntry 4 }
dot11STBCControlFrameOptionImplemented OBJECT-TYPE
SYNTAX TruthValue
MAX-ACCESS read-only
STATUS current
DESCRIPTION
"This is a capability variable.
Its value is determined by device capabilities.
This attribute, when true, indicates that the station implementation is
capable of processing the received control frames that are STBC frames."
DEFVAL { false }
::= { dot11HTStationConfigEntry 5 }
dot11LsigTxopProtectionOptionImplemented OBJECT-TYPE
SYNTAX TruthValue
MAX-ACCESS read-only
STATUS current
DESCRIPTION
"This is a capability variable.
Its value is determined by device capabilities.
This attribute, when true, indicates that the station implementation is
capable of supporting L-SIG TXOP protection option."
DEFVAL { false }
::= { dot11HTStationConfigEntry 6 }
dot11MaxRxAMPDUFactor OBJECT-TYPE
SYNTAX Unsigned32 (0..3)
MAX-ACCESS read-only
STATUS current
DESCRIPTION
"This is a capability variable.
Its value is determined by device capabilities.
This attribute indicates the maximum length of A-MPDU that the STA can
receive. The Maximum Rx A-MPDU defined by this field is equal to 2 **
(13+dot11MaxRxAMPDUFactor) -1 octets."
DEFVAL { 0 }
::= { dot11HTStationConfigEntry 7 }
dot11MinimumMPDUStartSpacing OBJECT-TYPE
SYNTAX Unsigned32 (0..7)
MAX-ACCESS read-only
STATUS current
DESCRIPTION
"This is a capability variable.
Its value is determined by device capabilities.
This attribute indicates the minimum time between the start of adjacent
MPDUs within an A-MPDU. This time is measured at the PHY-SAP; the number
of octets between the start of two consecutive MPDUs in A-MPDU shall be
equal or greater than (dot11MinimumMPDUStartSpacing*PHY-bit-rate)/8. The
encoding of the minimum time to this attribute is:
0 - no restriction
1 - 1/4 microsecond
2 - 1/2 microsecond
3 - 1 microsecond
4 - 2 microseconds
5 - 4 microseconds
6 - 8 microseconds
7 - 16 microseconds"
DEFVAL { 0 }
::= { dot11HTStationConfigEntry 8 }
dot11PCOOptionImplemented OBJECT-TYPE
SYNTAX TruthValue
MAX-ACCESS read-only
STATUS current
DESCRIPTION
"This is a capability variable.
Its value is determined by device capabilities.
This attribute, when true, indicates that the station implementation is
capable of supporting PCO."
DEFVAL { false }
::= { dot11HTStationConfigEntry 9 }
dot11TransitionTime OBJECT-TYPE
SYNTAX Unsigned32 (0..3)
MAX-ACCESS read-only
STATUS current
DESCRIPTION
"This is a capability variable.
Its value is determined by device capabilities.
This attribute indicates that the maximum transition time within which the
STA can switch between 20 MHz channel width and 40 MHz channel width with
a high probability. The encoding of the transition time to this attribute
is:
0 - no transition
1 - 400 microsecondss
2 - 1500 microseconds
3 - 5000 microseconds"
DEFVAL { 2 }
::= { dot11HTStationConfigEntry 10 }
dot11MCSFeedbackOptionImplemented OBJECT-TYPE
SYNTAX INTEGER { none(0), unsolicited (2), both (3) }
MAX-ACCESS read-only
STATUS current
DESCRIPTION
"This is a capability variable.
Its value is determined by device capabilities.
This attribute indicates the MCS feed back capability supported by the
station implementation."
DEFVAL { 0 }
::= { dot11HTStationConfigEntry 11 }
dot11HTControlFieldSupported OBJECT-TYPE
SYNTAX TruthValue
MAX-ACCESS read-only
STATUS current
DESCRIPTION
"This is a capability variable.
Its value is determined by device capabilities.
This attribute, when true, indicates that the station implementation is
capable of receiving HT Control field."
DEFVAL { false }
::= { dot11HTStationConfigEntry 12 }
dot11RDResponderOptionImplemented OBJECT-TYPE
SYNTAX TruthValue
MAX-ACCESS read-only
STATUS current
DESCRIPTION
"This is a capability variable.
Its value is determined by device capabilities.
This attribute, when true, indicates that the station implementation is
capable operating as an RD responder."
DEFVAL { false }
::= { dot11HTStationConfigEntry 13 }
dot11SPPAMSDUCapable OBJECT-TYPE
SYNTAX TruthValue
MAX-ACCESS read-only
STATUS current
DESCRIPTION
"This is a capability variable.
Its value is determined by device capabilities.
This attribute, when true, indicates that the STA implementation is capable
of protecting the A-MSDU bit (Bit 7) in the QoS Control field when
dot11RSNAActivated is true."
DEFVAL { false }
::= { dot11HTStationConfigEntry 14 }
dot11SPPAMSDURequired OBJECT-TYPE
SYNTAX TruthValue
MAX-ACCESS read-write
STATUS current
DESCRIPTION
"This is a control variable.
It is written by an external management entity.
Changes take effect as soon as practical in the implementation.
This attribute, when true, indicates that the STA is configured to disallow
(i.e., not to send or receive) PP A-MSDUs when dot11RSNAActivated is
true."
DEFVAL { false }
::= { dot11HTStationConfigEntry 15 }
dot11FortyMHzOptionImplemented OBJECT-TYPE
SYNTAX TruthValue
MAX-ACCESS read-only
STATUS current
DESCRIPTION
"This is a capability variable.
Its value is determined by device capabilities.
This attribute, when true, indicates that the STA is capable of transmitting
and receiving on a 40 MHz channel using a 40 MHz mask."
DEFVAL { false }
::= { dot11HTStationConfigEntry 16 }
-- **********************************************************************
-- * End of dot11HTStationConfig TABLE
-- **********************************************************************
-- **********************************************************************
-- * dot11WirelessMgmtOptions TABLE
-- **********************************************************************
dot11WirelessMgmtOptionsTable OBJECT-TYPE
SYNTAX SEQUENCE OF Dot11WirelessMgmtOptionsEntry
MAX-ACCESS not-accessible
STATUS current
DESCRIPTION
"Wireless Management attributes. In tabular form to allow for multiple
instances on an agent. This table only applies to the interface if
dot11WirelessManagementImplemented is set to true in the
dot11StationConfigTable. Otherwise this table should be ignored."
::= { dot11smt 18 }
dot11WirelessMgmtOptionsEntry OBJECT-TYPE
SYNTAX Dot11WirelessMgmtOptionsEntry
MAX-ACCESS not-accessible
STATUS current
DESCRIPTION
"An entry in the dot11WirelessMgmtOptionsTable. For all Wireless Management
features, an Activated MIB variable is used to activate/enable or deactivate/
disable the corresponding feature. An Implemented MIB variable is
used for an optional feature to indicate whether the feature is implemented.
A mandatory feature does not have a corresponding Implemented MIB
variable. It is possible for there to be multiple IEEE 802.11 interfaces
on one agent, each with its unique MAC address. The relationship between
an IEEE 802.11 interface and an interface in the context of the Internetstandard
MIB is one-to-one. As such, the value of an ifIndex object
instance can be directly used to identify corresponding instances of the
objects defined herein. ifIndex - Each IEEE 802.11 interface is represented
by an ifEntry. Interface tables in this MIB module are indexed by
ifIndex."
INDEX { ifIndex }
::= { dot11WirelessMgmtOptionsTable 1 }
Dot11WirelessMgmtOptionsEntry ::=
SEQUENCE {
dot11MgmtOptionLocationActivated TruthValue,
dot11MgmtOptionFMSImplemented TruthValue,
dot11MgmtOptionFMSActivated TruthValue,
dot11MgmtOptionEventsActivated TruthValue,
dot11MgmtOptionDiagnosticsActivated TruthValue,
dot11MgmtOptionMultiBSSIDImplemented TruthValue,
dot11MgmtOptionMultiBSSIDActivated TruthValue,
dot11MgmtOptionTFSImplemented TruthValue,
dot11MgmtOptionTFSActivated TruthValue,
dot11MgmtOptionWNMSleepModeImplemented TruthValue,
dot11MgmtOptionWNMSleepModeActivated TruthValue,
dot11MgmtOptionTIMBroadcastImplemented TruthValue,
dot11MgmtOptionTIMBroadcastActivated TruthValue,
dot11MgmtOptionProxyARPImplemented TruthValue,
dot11MgmtOptionProxyARPActivated TruthValue,
dot11MgmtOptionBSSTransitionImplemented TruthValue,
dot11MgmtOptionBSSTransitionActivated TruthValue,
dot11MgmtOptionQoSTrafficCapabilityImplemented TruthValue,
dot11MgmtOptionQoSTrafficCapabilityActivated TruthValue,
dot11MgmtOptionACStationCountImplemented TruthValue,
dot11MgmtOptionACStationCountActivated TruthValue,
dot11MgmtOptionCoLocIntfReportingImplemented TruthValue,
dot11MgmtOptionCoLocIntfReportingActivated TruthValue,
dot11MgmtOptionMotionDetectionImplemented TruthValue,
dot11MgmtOptionMotionDetectionActivated TruthValue,
dot11MgmtOptionTODImplemented TruthValue,
dot11MgmtOptionTODActivated TruthValue,
dot11MgmtOptionTimingMsmtImplemented TruthValue,
dot11MgmtOptionTimingMsmtActivated TruthValue,
dot11MgmtOptionChannelUsageImplemented TruthValue,
dot11MgmtOptionChannelUsageActivated TruthValue,
dot11MgmtOptionTriggerSTAStatisticsActivated TruthValue,
dot11MgmtOptionSSIDListImplemented TruthValue,
dot11MgmtOptionSSIDListActivated TruthValue,
dot11MgmtOptionMulticastDiagnosticsActivated TruthValue,
dot11MgmtOptionLocationTrackingImplemented TruthValue,
dot11MgmtOptionLocationTrackingActivated TruthValue,
dot11MgmtOptionDMSImplemented TruthValue,
dot11MgmtOptionDMSActivated TruthValue,
dot11MgmtOptionUAPSDCoexistenceImplemented TruthValue,
dot11MgmtOptionUAPSDCoexistenceActivated TruthValue,
dot11MgmtOptionWNMNotificationImplemented TruthValue,
dot11MgmtOptionWNMNotificationActivated TruthValue,
dot11MgmtOptionUTCTSFOffsetImplemented TruthValue,
dot11MgmtOptionUTCTSFOffsetActivated TruthValue
}
dot11MgmtOptionLocationActivated OBJECT-TYPE
SYNTAX TruthValue
MAX-ACCESS read-write
STATUS current
DESCRIPTION
"This is a control variable.
It is written by an external management entity or the SME.
Changes take effect as soon as practical in the implementation.
This attribute, when true, indicates that the capability of the station to
provide location is enabled. The capability is disabled, otherwise."
DEFVAL { false}
::= { dot11WirelessMgmtOptionsEntry 1 }
dot11MgmtOptionFMSImplemented OBJECT-TYPE
SYNTAX TruthValue
MAX-ACCESS read-only
STATUS current
DESCRIPTION
"This is a capability variable.
Its value is determined by device capabilities.
This attribute, when true, indicates that the station implementation is
capable of supporting FMS when the dot11WirelessManagementImplemented is
set to true."
::= { dot11WirelessMgmtOptionsEntry 2 }
dot11MgmtOptionFMSActivated OBJECT-TYPE
SYNTAX TruthValue
MAX-ACCESS read-write
STATUS current
DESCRIPTION
"This is a control variable.
It is written by an external management entity or the SME.
Changes take effect as soon as practical in the implementation.
This attribute, when true, indicates that the capability of the station to
provide FMS is enabled. The capability is disabled, otherwise"
DEFVAL { false}
::= { dot11WirelessMgmtOptionsEntry 3 }
dot11MgmtOptionEventsActivated OBJECT-TYPE
SYNTAX TruthValue
MAX-ACCESS read-write
STATUS current
DESCRIPTION
"This is a control variable.
It is written by an external management entity or the SME.
Changes take effect as soon as practical in the implementation.
This attribute, when true, indicates that the capability of the station to
provide Event Reporting is enabled. The capability is disabled, otherwise"
DEFVAL { false}
::= { dot11WirelessMgmtOptionsEntry 4 }
dot11MgmtOptionDiagnosticsActivated OBJECT-TYPE
SYNTAX TruthValue
MAX-ACCESS read-write
STATUS current
DESCRIPTION
"This is a control variable.
It is written by an external management entity or the SME.
Changes take effect as soon as practical in the implementation.
This attribute, when true, indicates that the capability of the station to
provide Diagnostic Reporting is enabled. The capability is disabled, otherwise."
DEFVAL { false}
::= { dot11WirelessMgmtOptionsEntry 5 }
dot11MgmtOptionMultiBSSIDImplemented OBJECT-TYPE
SYNTAX TruthValue
MAX-ACCESS read-only
STATUS current
DESCRIPTION
"This is a capability variable.
Its value is determined by device capabilities.
This attribute, when true, indicates that the station implementation is
capable of supporting Multiple BSSID when the
dot11WirelessManagementImplemented is set to true."
::= { dot11WirelessMgmtOptionsEntry 6 }
dot11MgmtOptionMultiBSSIDActivated OBJECT-TYPE
SYNTAX TruthValue
MAX-ACCESS read-write
STATUS current
DESCRIPTION
"This is a control variable.
It is written by an external management entity or the SME.
Changes take effect as soon as practical in the implementation.
This attribute, when true, indicates that the capability of the station to
provide Multi BSSID is enabled. The capability is disabled, otherwise."
DEFVAL { false}
::= { dot11WirelessMgmtOptionsEntry 7 }
dot11MgmtOptionTFSImplemented OBJECT-TYPE
SYNTAX TruthValue
MAX-ACCESS read-only
STATUS current
DESCRIPTION
"This is a capability variable.
Its value is determined by device capabilities.
This attribute, when true, indicates that the station implementation is
capable of supporting TFS when the dot11WirelessManagementImplemented is
set to true."
::= { dot11WirelessMgmtOptionsEntry 8 }
dot11MgmtOptionTFSActivated OBJECT-TYPE
SYNTAX TruthValue
MAX-ACCESS read-write
STATUS current
DESCRIPTION
"This is a control variable.
It is written by an external management entity or the SME.
Changes take effect as soon as practical in the implementation.
This attribute, when true, indicates that TFS is enabled. TFS is disabled
otherwise."
DEFVAL { false}
::= { dot11WirelessMgmtOptionsEntry 9 }
dot11MgmtOptionWNMSleepModeImplemented OBJECT-TYPE
SYNTAX TruthValue
MAX-ACCESS read-only
STATUS current
DESCRIPTION
"This is a capability variable.
Its value is determined by device capabilities.
This attribute, when true, indicates that the station implementation is
capable of supporting WNMSleep Mode when the
dot11WirelessManagementImplemented is set to true."
::= { dot11WirelessMgmtOptionsEntry 10 }
dot11MgmtOptionWNMSleepModeActivated OBJECT-TYPE
SYNTAX TruthValue
MAX-ACCESS read-write
STATUS current
DESCRIPTION
"This is a control variable.
It is written by an external management entity or the SME.
Changes take effect as soon as practical in the implementation.
This attribute, when true, indicates that WNMSleep Mode is enabled.
WNMSleep Mode is disabled otherwise."
DEFVAL { false}
::= { dot11WirelessMgmtOptionsEntry 11 }
dot11MgmtOptionTIMBroadcastImplemented OBJECT-TYPE
SYNTAX TruthValue
MAX-ACCESS read-only
STATUS current
DESCRIPTION
"This is a capability variable.
Its value is determined by device capabilities.
This attribute, when true, indicates that the station implementation is
capable of supporting TIM Broadcast when the
dot11WirelessManagementImplemented is set to true."
::= { dot11WirelessMgmtOptionsEntry 12}
dot11MgmtOptionTIMBroadcastActivated OBJECT-TYPE
SYNTAX TruthValue
MAX-ACCESS read-write
STATUS current
DESCRIPTION
"This is a control variable.
It is written by an external management entity or the SME.
Changes take effect as soon as practical in the implementation.
This attribute, when true, indicates that TIM broadcast is enabled. TIM
broadcast is disabled otherwise."
DEFVAL { false}
::= { dot11WirelessMgmtOptionsEntry 13}
dot11MgmtOptionProxyARPImplemented OBJECT-TYPE
SYNTAX TruthValue
MAX-ACCESS read-only
STATUS current
DESCRIPTION
"This is a capability variable.
Its value is determined by device capabilities.
This attribute, when true, indicates that the station implementation is
capable of supporting the Proxy ARP service, when the
dot11WirelessManagementImplemented is set to true."
::= { dot11WirelessMgmtOptionsEntry 14 }
dot11MgmtOptionProxyARPActivated OBJECT-TYPE
SYNTAX TruthValue
MAX-ACCESS read-write
STATUS current
DESCRIPTION
"This is a control variable.
It is written by an external management entity or the SME.
Changes take effect as soon as practical in the implementation.
This attribute, when true, indicates that the capability of the AP to provide
the Proxy ARP service is enabled. The capability is disabled, otherwise."
DEFVAL { false}
::= { dot11WirelessMgmtOptionsEntry 15 }
dot11MgmtOptionBSSTransitionImplemented OBJECT-TYPE
SYNTAX TruthValue
MAX-ACCESS read-only
STATUS current
DESCRIPTION
"This is a capability variable.
Its value is determined by device capabilities.
This is a capability variable. Its value is determined by device capabilities.
This attribute, when true, indicates that the station implementation
is capable of supporting BSS Transition Management, when the
dot11WirelessManagementImplemented is set to true."
::= { dot11WirelessMgmtOptionsEntry 16 }
dot11MgmtOptionBSSTransitionActivated OBJECT-TYPE
SYNTAX TruthValue
MAX-ACCESS read-write
STATUS current
DESCRIPTION
"This is a control variable.
It is written by an external management entity or the SME.
Changes take effect as soon as practical in the implementation.
This attribute, when true, indicates that the capability of the station to
provide BSS Transition is enabled. The capability is disabled, otherwise.
"
DEFVAL { false}
::= { dot11WirelessMgmtOptionsEntry 17 }
dot11MgmtOptionQoSTrafficCapabilityImplemented OBJECT-TYPE
SYNTAX TruthValue
MAX-ACCESS read-only
STATUS current
DESCRIPTION
"This is a capability variable.
Its value is determined by device capabilities.
This attribute, when true, indicates that the station implementation is
capable of supporting QoS Traffic Capability when the
dot11WirelessManagementImplemented is set to true."
::= { dot11WirelessMgmtOptionsEntry 18 }
dot11MgmtOptionQoSTrafficCapabilityActivated OBJECT-TYPE
SYNTAX TruthValue
MAX-ACCESS read-write
STATUS current
DESCRIPTION
"This is a control variable.
It is written by an external management entity or the SME.
Changes take effect as soon as practical in the implementation.
This attribute, when true, indicates that the capability of the station to
provide QoS Traffic Capability is enabled. QoS Traffic Capability is disabled
otherwise."
DEFVAL { false}
::= { dot11WirelessMgmtOptionsEntry 19 }
dot11MgmtOptionACStationCountImplemented OBJECT-TYPE
SYNTAX TruthValue
MAX-ACCESS read-only
STATUS current
DESCRIPTION
"This is a capability variable.
Its value is determined by device capabilities.
This attribute, when true, indicates that the station implementation is
capable of supporting AC Station Count when the
dot11WirelessManagementImplemented is set to true."
::= { dot11WirelessMgmtOptionsEntry 20 }
dot11MgmtOptionACStationCountActivated OBJECT-TYPE
SYNTAX TruthValue
MAX-ACCESS read-write
STATUS current
DESCRIPTION
"This is a control variable.
It is written by an external management entity or the SME.
Changes take effect as soon as practical in the implementation.
This attribute, when true, indicates that the capability of the station to
provide AC Station Count is enabled. AC Station Count is disabled otherwise."
DEFVAL { false}
::= { dot11WirelessMgmtOptionsEntry 21 }
dot11MgmtOptionCoLocIntfReportingImplemented OBJECT-TYPE
SYNTAX TruthValue
MAX-ACCESS read-only
STATUS current
DESCRIPTION
"This is a capability variable.
Its value is determined by device capabilities.
This attribute, when true, indicates that the station implementation is
capable of supporting Colocated Interference Reporting. The capability is
disabled, otherwise."
::= { dot11WirelessMgmtOptionsEntry 22 }
dot11MgmtOptionCoLocIntfReportingActivated OBJECT-TYPE
SYNTAX TruthValue
MAX-ACCESS read-write
STATUS current
DESCRIPTION
"This is a control variable.
It is written by an external management entity or the SME.
Changes take effect as soon as practical in the implementation.
This attribute, when true, indicates that the capability of the station to
support Colocated Interference Reporting is enabled. The capability is
disabled, otherwise."
DEFVAL { false}
::= { dot11WirelessMgmtOptionsEntry 23 }
dot11MgmtOptionMotionDetectionImplemented OBJECT-TYPE
SYNTAX TruthValue
MAX-ACCESS read-only
STATUS current
DESCRIPTION
"This is a capability variable.
Its value is determined by device capabilities.
This attribute, when true, indicates that the station implementation is
capable of supporting motion detection when the
dot11WirelessManagementImplemented is set to true. "
::= { dot11WirelessMgmtOptionsEntry 24 }
dot11MgmtOptionMotionDetectionActivated OBJECT-TYPE
SYNTAX TruthValue
MAX-ACCESS read-write
STATUS current
DESCRIPTION
"This is a control variable.
It is written by an external management entity or the SME.
Changes take effect as soon as practical in the implementation.
This attribute, when true, indicates that the capability to support motion
detection is enabled."
DEFVAL { false}
::= { dot11WirelessMgmtOptionsEntry 25 }
dot11MgmtOptionTODImplemented OBJECT-TYPE
SYNTAX TruthValue
MAX-ACCESS read-only
STATUS current
DESCRIPTION
"This is a capability variable.
Its value is determined by device capabilities.
This attribute, when true, indicates that the station implementation is
capable of supporting Time Of Departure for Clause 16 transmitted frames,
Clause 18 transmitted frames, Clause 17 transmitted frames, Clause 19
transmitted frames and Clause 20 transmitted frames when the
dot11WirelessManagementImplemented is set to true."
::= { dot11WirelessMgmtOptionsEntry 26 }
dot11MgmtOptionTODActivated OBJECT-TYPE
SYNTAX TruthValue
MAX-ACCESS read-write
STATUS current
DESCRIPTION
"This is a control variable.
It is written by an external management entity or the SME.
Changes take effect as soon as practical in the implementation.
This attribute, when true, indicates that the capability to support Time
Of Departure frames for transmitted Clause 16, Clause 18, Clause 17,
Clause 19 and Clause 20 frames is enabled."
DEFVAL { false}
::= { dot11WirelessMgmtOptionsEntry 27 }
dot11MgmtOptionTimingMsmtImplemented OBJECT-TYPE
SYNTAX TruthValue
MAX-ACCESS read-only
STATUS current
DESCRIPTION
"This is a capability variable.
Its value is determined by device capabilities.
This attribute, when true, indicates that the station implementation is
capable of supporting Timing Measurement capability when the
dot11WirelessManagementImplemented is set to true."
::= { dot11WirelessMgmtOptionsEntry 28 }
dot11MgmtOptionTimingMsmtActivated OBJECT-TYPE
SYNTAX TruthValue
MAX-ACCESS read-write
STATUS current
DESCRIPTION
"This is a control variable.
It is written by an external management entity or the SME.
Changes take effect as soon as practical in the implementation.
This attribute, when true, indicates that the station capability for Timing
Measurement is enabled. False indicates the station has no Timing Measurement
capability or that the capability is present but is disabled."
DEFVAL { false}
::= { dot11WirelessMgmtOptionsEntry 29 }
dot11MgmtOptionChannelUsageImplemented OBJECT-TYPE
SYNTAX TruthValue
MAX-ACCESS read-only
STATUS current
DESCRIPTION
"This is a capability variable.
Its value is determined by device capabilities.
This attribute, when true, indicates that the station implementation is
capable of supporting Channel Usage when the
dot11WirelessManagementImplemented is set to true."
::= { dot11WirelessMgmtOptionsEntry 30 }
dot11MgmtOptionChannelUsageActivated OBJECT-TYPE
SYNTAX TruthValue
MAX-ACCESS read-write
STATUS current
DESCRIPTION
"This is a control variable.
It is written by an external management entity or the SME.
Changes take effect as soon as practical in the implementation.
This attribute, when true, indicates that Channel Usage is enabled. Channel
Usage is disabled otherwise."
DEFVAL { false}
::= { dot11WirelessMgmtOptionsEntry 31 }
dot11MgmtOptionTriggerSTAStatisticsActivated OBJECT-TYPE
SYNTAX TruthValue
MAX-ACCESS read-write
STATUS current
DESCRIPTION
"This is a control variable.
It is written by an external management entity or the SME.
Changes take effect as soon as practical in the implementation.
This attribute, when true, indicates that the capability of the station to
provide triggered STA statistics is enabled. The capability is disabled
otherwise"
DEFVAL { false}
::= { dot11WirelessMgmtOptionsEntry 32 }
dot11MgmtOptionSSIDListImplemented OBJECT-TYPE
SYNTAX TruthValue
MAX-ACCESS read-only
STATUS current
DESCRIPTION
"This is a capability variable.
Its value is determined by device capabilities.
This attribute, when true, indicates that the station implementation is
capable of supporting the SSID List capability when the
dot11WirelessManagementImplemented is true."
::= { dot11WirelessMgmtOptionsEntry 33 }
dot11MgmtOptionSSIDListActivated OBJECT-TYPE
SYNTAX TruthValue
MAX-ACCESS read-write
STATUS current
DESCRIPTION
"This is a control variable.
It is written by an external management entity or the SME.
Changes take effect as soon as practical in the implementation.
This attribute, when true, indicates that the capability of the station to
support the SSID List capability is enabled. The capability is disabled,
otherwise"
DEFVAL { false}
::= { dot11WirelessMgmtOptionsEntry 34 }
dot11MgmtOptionMulticastDiagnosticsActivated OBJECT-TYPE
SYNTAX TruthValue
MAX-ACCESS read-write
STATUS current
DESCRIPTION
"This is a control variable.
It is written by an external management entity or the SME.
Changes take effect as soon as practical in the implementation.
This attribute, when true, indicates that the capability of the station to
provide Multicast Diagnostic Reporting is enabled. The capability is disabled,
otherwise."
DEFVAL { false}
::= { dot11WirelessMgmtOptionsEntry 35 }
dot11MgmtOptionLocationTrackingImplemented OBJECT-TYPE
SYNTAX TruthValue
MAX-ACCESS read-only
STATUS current
DESCRIPTION
"This is a capability variable.
Its value is determined by device capabilities.
This attribute, when true, indicates that the station implementation is
capable of supporting Location Track when the
dot11WirelessManagementImplemented is true."
::= { dot11WirelessMgmtOptionsEntry 36 }
dot11MgmtOptionLocationTrackingActivated OBJECT-TYPE
SYNTAX TruthValue
MAX-ACCESS read-write
STATUS current
DESCRIPTION
"This is a control variable.
It is written by an external management entity or the SME.
Changes take effect as soon as practical in the implementation.
This attribute, when true, indicates that the capability of the station to
provide Location Track is enabled. The capability is disabled otherwise."
DEFVAL { false}
::= { dot11WirelessMgmtOptionsEntry 37 }
dot11MgmtOptionDMSImplemented OBJECT-TYPE
SYNTAX TruthValue
MAX-ACCESS read-only
STATUS current
DESCRIPTION
"This is a capability variable.
Its value is determined by device capabilities.
This attribute, when true, indicates that the station implementation is
capable of supporting DMS when the dot11WirelessManagementImplemented is
true."
::= { dot11WirelessMgmtOptionsEntry 38 }
dot11MgmtOptionDMSActivated OBJECT-TYPE
SYNTAX TruthValue
MAX-ACCESS read-write
STATUS current
DESCRIPTION
"This is a control variable.
It is written by an external management entity or the SME.
Changes take effect as soon as practical in the implementation.
This attribute, when true, indicates that DMS is enabled. DMS is disabled
otherwise."
DEFVAL { false}
::= { dot11WirelessMgmtOptionsEntry 39 }
dot11MgmtOptionUAPSDCoexistenceImplemented OBJECT-TYPE
SYNTAX TruthValue
MAX-ACCESS read-only
STATUS current
DESCRIPTION
"This is a capability variable.
Its value is determined by device capabilities.
This attribute, when true, indicates that the Station implementation is
capable of supporting U-APSD Coexistence when the
dot11WirelessManagementImplemented is set to true."
::= { dot11WirelessMgmtOptionsEntry 40}
dot11MgmtOptionUAPSDCoexistenceActivated OBJECT-TYPE
SYNTAX TruthValue
MAX-ACCESS read-write
STATUS current
DESCRIPTION
"This is a control variable.
It is written by an external management entity or the SME.
Changes take effect as soon as practical in the implementation.
This attribute, when true, indicates that U-APSD Coexistence is enabled.
U-APSD Coexistence is disabled, otherwise."
DEFVAL { false}
::= { dot11WirelessMgmtOptionsEntry 41}
dot11MgmtOptionWNMNotificationImplemented OBJECT-TYPE
SYNTAX TruthValue
MAX-ACCESS read-only
STATUS current
DESCRIPTION
"This is a capability variable.
Its value is determined by device capabilities.
This attribute, when true, indicates that the station implementation is
capable of supporting WNM-Notification when the
dot11WirelessManagementImplemented is set to true."
::= { dot11WirelessMgmtOptionsEntry 42}
dot11MgmtOptionWNMNotificationActivated OBJECT-TYPE
SYNTAX TruthValue
MAX-ACCESS read-write
STATUS current
DESCRIPTION
"This is a control variable.
It is written by an external management entity or the SME.
Changes take effect as soon as practical in the implementation.
This attribute, when true, indicates that the capability of the station to
provide WNM-Notification is enabled. The capability is disabled, otherwise."
DEFVAL { false}
::= { dot11WirelessMgmtOptionsEntry 43}
dot11MgmtOptionUTCTSFOffsetImplemented OBJECT-TYPE
SYNTAX TruthValue
MAX-ACCESS read-only
STATUS current
DESCRIPTION
"This is a capability variable.
Its value is determined by device capabilities.
This attribute, when true, indicates that the Station implementation is
capable of supporting UTC TSF Offset advertisement when the
dot11WirelessManagementImplemented is set to true."
::= { dot11WirelessMgmtOptionsEntry 44}
dot11MgmtOptionUTCTSFOffsetActivated OBJECT-TYPE
SYNTAX TruthValue
MAX-ACCESS read-write
STATUS current
DESCRIPTION
"This is a control variable.
It is written by an external management entity or the SME.
Changes take effect as soon as practical in the implementation.
This attribute, when true, indicates that UTC TSF Offset advertisement is
enabled at the station. The capability is disabled, otherwise."
DEFVAL { false}
::= { dot11WirelessMgmtOptionsEntry 45}
-- ********************************************************************
-- * dot11LocationServices TABLE
-- ********************************************************************
dot11LocationServicesNextIndex OBJECT-TYPE
SYNTAX Unsigned32 (0..4294967295)
MAX-ACCESS read-only
STATUS current
DESCRIPTION
"Identifies a hint for the next value of dot11LocationServicesIndex to be
used in a row creation attempt for dot11LocationServicesTable. If no new
rows can be created for some reason, such as memory, processing requirements,
etc, the SME shall set this attribute to 0. It shall update this
attribute to a proper value other than 0 as soon as it is capable of
receiving new measurement requests. The nextIndex is not necessarily
sequential nor monotonically increasing."
::= { dot11smt 19 }
dot11LocationServicesTable OBJECT-TYPE
SYNTAX SEQUENCE OF Dot11LocationServicesEntry
MAX-ACCESS not-accessible
STATUS current
DESCRIPTION
"Group contains conceptual table of attributes for
WNM LocationServices."
::= { dot11smt 20 }
dot11LocationServicesEntry OBJECT-TYPE
SYNTAX Dot11LocationServicesEntry
MAX-ACCESS not-accessible
STATUS current
DESCRIPTION
"An entry in the dot11LocationServicesTable
Indexed by dot11LocationServicesIndex."
INDEX { dot11LocationServicesIndex }
::= { dot11LocationServicesTable 1 }
Dot11LocationServicesEntry ::=
SEQUENCE {
dot11LocationServicesIndex Unsigned32,
dot11LocationServicesMACAddress MacAddress,
dot11LocationServicesLIPIndicationMulticastAddress MacAddress,
dot11LocationServicesLIPReportIntervalUnits INTEGER,
dot11LocationServicesLIPNormalReportInterval Unsigned32,
dot11LocationServicesLIPNormalFramesperChannel Unsigned32,
dot11LocationServicesLIPInMotionReportInterval Unsigned32,
dot11LocationServicesLIPInMotionFramesperChannel Unsigned32,
dot11LocationServicesLIPBurstInterframeInterval Unsigned32,
dot11LocationServicesLIPTrackingDuration Unsigned32,
dot11LocationServicesLIPEssDetectionInterval Unsigned32,
dot11LocationServicesLocationIndicationChannelList OCTET STRING,
dot11LocationServicesLocationIndicationBroadcastDataRate
Unsigned32,
dot11LocationServicesLocationIndicationOptionsUsed OCTET STRING,
dot11LocationServicesLocationIndicationIndicationParameters
OCTET STRING,
dot11LocationServicesLocationStatus Unsigned32
}
dot11LocationServicesIndex OBJECT-TYPE
SYNTAX Unsigned32 (1..4294967295)
MAX-ACCESS not-accessible
STATUS current
DESCRIPTION
"This attribute contains an auxiliary index into the
dot11LocationServicesTable."
::= { dot11LocationServicesEntry 1 }
dot11LocationServicesMACAddress OBJECT-TYPE
SYNTAX MacAddress
MAX-ACCESS read-create
STATUS current
DESCRIPTION
"This attribute is the MAC address of the STA reporting location information."
::= { dot11LocationServicesEntry 2 }
dot11LocationServicesLIPIndicationMulticastAddress OBJECT-TYPE
SYNTAX MacAddress
MAX-ACCESS read-create
STATUS current
DESCRIPTION
"This attribute is the destination address to which the Location Track
Notification frames are sent in a non-IBSS network; see 8.4.2.73.2 and
10.23.4.1."
::= { dot11LocationServicesEntry 3 }
dot11LocationServicesLIPReportIntervalUnits OBJECT-TYPE
SYNTAX INTEGER {
hours(0),
minutes(1),
seconds(2),
milliseconds(3)
}
MAX-ACCESS read-create
STATUS current
DESCRIPTION
"This attribute contains the Location Indication Parameters Report Interval
Units value."
::= { dot11LocationServicesEntry 4 }
dot11LocationServicesLIPNormalReportInterval OBJECT-TYPE
SYNTAX Unsigned32 (0..65535)
MAX-ACCESS read-create
STATUS current
DESCRIPTION
"This attribute contains the time interval, expressed in the units indicated
in the Report Interval Units field, at which the reporting STA is
expected to transmit one or more Location Track Notification frames if
either dot11MgmtOptionMotionDetectionActivated is false or the STA is stationary.
The STA will not transmit Location Track Notification frames when
the Normal Report Interval is 0."
::= { dot11LocationServicesEntry 5 }
dot11LocationServicesLIPNormalFramesperChannel OBJECT-TYPE
SYNTAX Unsigned32 (0..255)
MAX-ACCESS read-create
STATUS current
DESCRIPTION
"This attribute contains the number of Location Track Notification frames
per channel sent or expected to be sent by the STA at each Normal Report
Interval."
::= { dot11LocationServicesEntry 6 }
dot11LocationServicesLIPInMotionReportInterval OBJECT-TYPE
SYNTAX Unsigned32 (0..65535)
MAX-ACCESS read-create
STATUS current
DESCRIPTION
"This attribute contains the time interval, expressed in the units indicated
in the Report Interval Units field, at which the STA reports its
location by sending a Location Track Notification frame when the reporting
STA is in motion. If dot11MgmtOptionMotionDetectionActivated is false,
this field is set to 0."
::= { dot11LocationServicesEntry 7}
dot11LocationServicesLIPInMotionFramesperChannel OBJECT-TYPE
SYNTAX Unsigned32 (0..255)
MAX-ACCESS read-create
STATUS current
DESCRIPTION
"This attribute contains the number of Location Track Notification frames
per channel sent or expected to be sent by the STA at each In-Motion
Report Interval. If dot11MgmtOptionMotionDetectionActivated is false, this
field is set to 0."
::= { dot11LocationServicesEntry 8 }
dot11LocationServicesLIPBurstInterframeInterval OBJECT-TYPE
SYNTAX Unsigned32 (0..255)
MAX-ACCESS read-create
STATUS current
DESCRIPTION
"This attribute contains the target time interval, expressed in milliseconds,
between the transmissions of each of the Normal or In-Motion frames
on the same channel. The Burst Inter-frame interval value is set to 0 to
indicate that frames will be transmitted with no target inter-frame
delay."
::= { dot11LocationServicesEntry 9 }
dot11LocationServicesLIPTrackingDuration OBJECT-TYPE
SYNTAX Unsigned32 (0..255)
MAX-ACCESS read-create
STATUS current
DESCRIPTION
"This attribute contains the amount of time, in minutes, that a STA sends
the Location Track Notification frames. The duration starts as soon as the
STA sends a Location Configuration Response frame with a Location Status
value of Success. If the Tracking Duration value is a nonzero value the
STA will send Location Track Notification Frames, based on the Normal and
In-Motion Report Interval field values, until the duration ends. If the
Tracking Duration is 0 the STA will continuously send Location Track Notification
frames as defined by Normal and In-Motion Report Interval field
values until transmission is terminated based on 10.23.4.2 procedures."
::= { dot11LocationServicesEntry 10}
dot11LocationServicesLIPEssDetectionInterval OBJECT-TYPE
SYNTAX Unsigned32 (0..255)
MAX-ACCESS read-create
STATUS current
DESCRIPTION
"This attribute contains the interval, in minutes, that a STA checks for
beacons transmitted by one or more APs belonging to the same ESS that configured
the STA. If no beacons from the ESS are received for this period,
the STA terminates transmission of Location Track Notification frames as
described in 10.23.4.2 procedures. The ESS Detection Interval field is not
used when the ESS Detection Interval field value is set to 0."
::= { dot11LocationServicesEntry 11}
dot11LocationServicesLocationIndicationChannelList OBJECT-TYPE
SYNTAX OCTET STRING (SIZE (2..254))
MAX-ACCESS read-create
STATUS current
DESCRIPTION
"This attribute contains one or more Operating Class and Channel octet
pairs."
::= { dot11LocationServicesEntry 12}
dot11LocationServicesLocationIndicationBroadcastDataRate OBJECT-TYPE
SYNTAX Unsigned32 (0..4294967295)
MAX-ACCESS read-create
STATUS current
DESCRIPTION
"This attribute specifies the target data rate at which the STA transmits
Location Track Notification Frames. The Broadcast Target Data Rate field
format is specified by the Rate Identification field defined in 8.4.1.32.
A value of 0 indicates the STA transmits Location Track Notification
frames at a rate chosen by the STA transmitting the Location Track Notification
frames."
DEFVAL { 0 }
::= { dot11LocationServicesEntry 13}
dot11LocationServicesLocationIndicationOptionsUsed OBJECT-TYPE
SYNTAX OCTET STRING (SIZE(1))
MAX-ACCESS read-create
STATUS current
DESCRIPTION
"This attribute indicates the location configuration options used for
transmitting Location Track Notification Frames."
::= { dot11LocationServicesEntry 14}
dot11LocationServicesLocationIndicationIndicationParameters OBJECT-TYPE
SYNTAX OCTET STRING (SIZE (1..255))
MAX-ACCESS read-create
STATUS current
DESCRIPTION
"This attribute indicates the location Indication Parameters used for
transmitting Location Track Notification Frames."
::= { dot11LocationServicesEntry 15}
dot11LocationServicesLocationStatus OBJECT-TYPE
SYNTAX Unsigned32 (0..255)
MAX-ACCESS read-only
STATUS current
DESCRIPTION
"This attribute contains the Location Status value as indicated in
Table 8-137, Event Report Status."
::= { dot11LocationServicesEntry 16 }
-- ********************************************************************
-- * End of dot11LocationServices TABLE
-- ********************************************************************
-- ********************************************************************
-- * dot11WirelessMGTEvent TABLE
-- ********************************************************************
dot11WirelessMGTEventTable OBJECT-TYPE
SYNTAX SEQUENCE OF Dot11WirelessMGTEventEntry
MAX-ACCESS not-accessible
STATUS current
DESCRIPTION
"Group contains the current list of WIRELESS Management reports that have
been received by the MLME. The report tables shall be maintained as FIFO
to preserve freshness, thus the rows in this table can be deleted for memory
constraints or other implementation constraints determined by the vendor.
New rows shall have different RprtIndex values than those deleted within
the range limitation of the index. One easy way is to monotonically
increase the EventIndex for new reports being written in the table."
::= { dot11smt 21 }
dot11WirelessMGTEventEntry OBJECT-TYPE
SYNTAX Dot11WirelessMGTEventEntry
MAX-ACCESS not-accessible
STATUS current
DESCRIPTION
"An entry in the dot11WirelessMGTEventTable
Indexed by dot11WirelessMGTEventIndex."
INDEX { dot11WirelessMGTEventIndex }
::= { dot11WirelessMGTEventTable 1 }
Dot11WirelessMGTEventEntry ::=
SEQUENCE {
dot11WirelessMGTEventIndex Unsigned32,
dot11WirelessMGTEventMACAddress MacAddress,
dot11WirelessMGTEventType INTEGER,
dot11WirelessMGTEventStatus INTEGER,
dot11WirelessMGTEventTSF TSFType,
dot11WirelessMGTEventUTCOffset OCTET STRING,
dot11WirelessMGTEventTimeError OCTET STRING,
dot11WirelessMGTEventTransitionSourceBSSID MacAddress,
dot11WirelessMGTEventTransitionTargetBSSID MacAddress,
dot11WirelessMGTEventTransitionTime Unsigned32,
dot11WirelessMGTEventTransitionReason INTEGER,
dot11WirelessMGTEventTransitionResult Unsigned32,
dot11WirelessMGTEventTransitionSourceRCPI Unsigned32,
dot11WirelessMGTEventTransitionSourceRSNI Unsigned32,
dot11WirelessMGTEventTransitionTargetRCPI Unsigned32,
dot11WirelessMGTEventTransitionTargetRSNI Unsigned32,
dot11WirelessMGTEventRSNATargetBSSID MacAddress,
dot11WirelessMGTEventRSNAAuthenticationType OCTET STRING,
dot11WirelessMGTEventRSNAEAPMethod OCTET STRING,
dot11WirelessMGTEventRSNAResult Unsigned32,
dot11WirelessMGTEventRSNARSNElement OCTET STRING,
dot11WirelessMGTEventPeerSTAAddress MacAddress,
dot11WirelessMGTEventPeerOperatingClass Unsigned32,
dot11WirelessMGTEventPeerChannelNumber Unsigned32,
dot11WirelessMGTEventPeerSTATxPower Integer32,
dot11WirelessMGTEventPeerConnectionTime Unsigned32,
dot11WirelessMGTEventPeerPeerStatus Unsigned32,
dot11WirelessMGTEventWNMLog OCTET STRING
}
dot11WirelessMGTEventIndex OBJECT-TYPE
SYNTAX Unsigned32 (1..4294967295)
MAX-ACCESS read-only
STATUS current
DESCRIPTION
"This attribute contains an auxiliary index into the
dot11WirelessMGTEventTable."
::= { dot11WirelessMGTEventEntry 1 }
dot11WirelessMGTEventMACAddress OBJECT-TYPE
SYNTAX MacAddress
MAX-ACCESS read-only
STATUS current
DESCRIPTION
"This attribute is the MAC address of the STA providing the Event Report."
::= { dot11WirelessMGTEventEntry 2 }
dot11WirelessMGTEventType OBJECT-TYPE
SYNTAX INTEGER {
transition(0),
rsna(1),
peerToPeer(2),
wnmLog(3),
vendorSpecific(221)
}
MAX-ACCESS read-only
STATUS current
DESCRIPTION
"This attribute indicates the request type of this WNM Event request."
::= { dot11WirelessMGTEventEntry 3 }
dot11WirelessMGTEventStatus OBJECT-TYPE
SYNTAX INTEGER {
successful(0),
requestFailed(1),
requestRefused(2),
requestIncapable(3),
detectedFrequentTransition(4)
}
MAX-ACCESS read-only
STATUS current
DESCRIPTION
"This attribute contains the status value included in the Event Report."
::= { dot11WirelessMGTEventEntry 4 }
dot11WirelessMGTEventTSF OBJECT-TYPE
SYNTAX TSFType
MAX-ACCESS read-only
STATUS current
DESCRIPTION
"This attribute contains the value of the Event timestamp field."
::= { dot11WirelessMGTEventEntry 5 }
dot11WirelessMGTEventUTCOffset OBJECT-TYPE
SYNTAX OCTET STRING (SIZE(10))
MAX-ACCESS read-only
STATUS current
DESCRIPTION
"This attribute indicates the UTC Offset Time Value optionally included in
the Event Report."
::= { dot11WirelessMGTEventEntry 6}
dot11WirelessMGTEventTimeError OBJECT-TYPE
SYNTAX OCTET STRING (SIZE(5))
MAX-ACCESS read-only
STATUS current
DESCRIPTION
"This attribute contains the value of the Event Time Error field optionally
included in the Event Report."
::= { dot11WirelessMGTEventEntry 7}
dot11WirelessMGTEventTransitionSourceBSSID OBJECT-TYPE
SYNTAX MacAddress
MAX-ACCESS read-only
STATUS current
DESCRIPTION
"This attribute contains the value of the Source BSSID field in a Transition
event report."
::= { dot11WirelessMGTEventEntry 8}
dot11WirelessMGTEventTransitionTargetBSSID OBJECT-TYPE
SYNTAX MacAddress
MAX-ACCESS read-only
STATUS current
DESCRIPTION
"This attribute contains the value of the Target BSSID field in a Transition
event report."
::= { dot11WirelessMGTEventEntry 9}
dot11WirelessMGTEventTransitionTime OBJECT-TYPE
SYNTAX Unsigned32 (0..65535)
UNITS "TUs"
MAX-ACCESS read-only
STATUS current
DESCRIPTION
"This attribute indicates the transition time for the reported transition
event in TUs. The Transition time is defined as the time difference
between the starting time and the ending time of a transition between APs,
even if the transition results in remaining on the same AP. Start and end
times for a transition event are defined in 10.23.2.2"
::= { dot11WirelessMGTEventEntry 10}
dot11WirelessMGTEventTransitionReason OBJECT-TYPE
SYNTAX INTEGER {
unspecified(0),
excessiveFrameLossRatesPoorConditions(1),
excessiveDelayForCurrentTrafficStreams(2),
insufficientQosCapacityForCurrentTrafficStreams(3),
firstAssociationToEss(4),
loadBalancing(5),
betterApFound(6),
deauthenticatedDisassociatedFromPreviousAp(7),
certificateToken(8),
apFailedIeee8021XEapAuthentication(9),
apFailed4wayHandshake(10),
excessiveDataMICFailures(11),
exceededFrameTransmissionRetryLimit(12),
ecessiveBroadcastDisassociations(13),
excessiveBroadcastDeauthentications(14),
previousTransitionFailed(15)
}
MAX-ACCESS read-only
STATUS current
DESCRIPTION
"This attribute indicates the reason for the reported BSS Transition
event. The format for this list of reasons is further detailed in
8.4.2.70.2."
::= { dot11WirelessMGTEventEntry 11}
dot11WirelessMGTEventTransitionResult OBJECT-TYPE
SYNTAX Unsigned32 (0..65535)
MAX-ACCESS read-only
STATUS current
DESCRIPTION
"This attribute indicates the result of the attempted transition and is
set to one of the status codes specified in Table 8-37."
::= { dot11WirelessMGTEventEntry 12 }
dot11WirelessMGTEventTransitionSourceRCPI OBJECT-TYPE
SYNTAX Unsigned32 (0..255)
MAX-ACCESS read-only
STATUS current
DESCRIPTION
"This attribute indicates the received channel power of the most recently
measured frame from the Source BSSID before the STA reassociates to the
Target BSSID. The Source RCPI is a logarithmic function of the received
signal power, as defined in the RCPI measurement subclause for the PHY
Type."
::= { dot11WirelessMGTEventEntry 13 }
dot11WirelessMGTEventTransitionSourceRSNI OBJECT-TYPE
SYNTAX Unsigned32 (0..255)
MAX-ACCESS read-only
STATUS current
DESCRIPTION
"This attribute indicates the received signal-to-noise indication of the
most recently measured frame from the Source BSSID before the STA reassociates
to the Target BSSID. The Source RSNI is a logarithmic function of
the signal-to-noise ratio, as defined in 8.4.2.43."
::= { dot11WirelessMGTEventEntry 14 }
dot11WirelessMGTEventTransitionTargetRCPI OBJECT-TYPE
SYNTAX Unsigned32 (0..255)
MAX-ACCESS read-only
STATUS current
DESCRIPTION
"This attribute indicates the received channel power of the first measured
frame just after STA reassociates to the Target BSSID. If association with
target BSSID failed, the Target RCPI field indicates the received channel
power of the most recently measured frame from the Target BSSID. The Target
RCPI is a logarithmic function of the received signal power, as
defined in the RCPI measurement subclause for the PHY Type."
::= { dot11WirelessMGTEventEntry 15 }
dot11WirelessMGTEventTransitionTargetRSNI OBJECT-TYPE
SYNTAX Unsigned32 (0..255)
MAX-ACCESS read-only
STATUS current
DESCRIPTION
"This attribute indicates the received signal-to-noise indication of the
first measured frame just after STA reassociates to the Target BSSID. If
association with target BSSID failed, the Target RCPI field indicates the
received signal-to-noise indication of the most recently measured frame
from the Target BSSID. The Target RSNI is a logarithmic function of the
signal-to-noise ratio, as defined in 8.4.2.43."
::= { dot11WirelessMGTEventEntry 16 }
dot11WirelessMGTEventRSNATargetBSSID OBJECT-TYPE
SYNTAX MacAddress
MAX-ACCESS read-only
STATUS current
DESCRIPTION
"This attribute contains the value of the Target BSSID field in an RSNA
event report."
::= { dot11WirelessMGTEventEntry 17 }
dot11WirelessMGTEventRSNAAuthenticationType OBJECT-TYPE
SYNTAX OCTET STRING (SIZE (4))
MAX-ACCESS read-only
STATUS current
DESCRIPTION
"This attribute indicates the AKM suite, as defined in Table 8-101. The
first three octets indicate the OUI. The last octet indicates the suite
type."
::= { dot11WirelessMGTEventEntry 18 }
dot11WirelessMGTEventRSNAEAPMethod OBJECT-TYPE
SYNTAX OCTET STRING(SIZE (1..8))
MAX-ACCESS read-only
STATUS current
DESCRIPTION
"This attribute indicates a value that identifies the EAP Method. When the
Authentication Type field is set to the value of either 00-0F-AC:1
(Authentication negotiated over IEEE 802.1X or using PMKSA caching as
defined in 11.5.9.3) or 00-0F-AC:3 (AKM suite selector for Fast BSS Transition
as defined in 11.6.1.7), the EAP Method field contains the IANA
assigned EAP type defined at http://www.iana.org/assignments/eap-numbers.
The EAP type contains either the legacy type (1 octet) or the expanded
type (1 octet type = 254, 3-octet Vendor ID, 4-octet Vendor-Type). The EAP
Method field is set to 0 otherwise."
::= { dot11WirelessMGTEventEntry 19 }
dot11WirelessMGTEventRSNAResult OBJECT-TYPE
SYNTAX Unsigned32 (0..65535)
MAX-ACCESS read-only
STATUS current
DESCRIPTION
"This attribute indicates the result of the RSNA event and is set to one
of the status codes specified in Table 8-37."
::= { dot11WirelessMGTEventEntry 20}
dot11WirelessMGTEventRSNARSNElement OBJECT-TYPE
SYNTAX OCTET STRING (SIZE(0..257))
MAX-ACCESS read-only
STATUS current
DESCRIPTION
"This attribute contains the entire contents of the negotiated RSNE at the
time of the authentication attempt. The format of the RSNE is defined in
8.4.2.27."
::= { dot11WirelessMGTEventEntry 21}
dot11WirelessMGTEventPeerSTAAddress OBJECT-TYPE
SYNTAX MacAddress
MAX-ACCESS read-only
STATUS current
DESCRIPTION
"This attribute indicates the MAC address of the peer STA or IBSS BSSID is
equal to the indicated MAC address. If this event is for a Peer-to-Peer
link in an infrastructure BSS, this field contains the MAC address of the
peer STA. If this event is for a Peer-to-Peer link in an IBSS, this field
contains the BSSID of the IBSS."
::= { dot11WirelessMGTEventEntry 22 }
dot11WirelessMGTEventPeerOperatingClass OBJECT-TYPE
SYNTAX Unsigned32 (1..255)
MAX-ACCESS read-only
STATUS current
DESCRIPTION
"This attribute indicates the channel set for this Peer-to-Peer Event
report. Country, Operating Class, and Channel Number together specify the
channel frequency and spacing for this measurement request. Valid values
of Operating Class are shown in Annex E."
::= { dot11WirelessMGTEventEntry 23 }
dot11WirelessMGTEventPeerChannelNumber OBJECT-TYPE
SYNTAX Unsigned32 (1..255)
MAX-ACCESS read-only
STATUS current
DESCRIPTION
"This attribute indicates the current operating channel for this Peer-to-
Peer Event report. The Channel Number is only defined within the indicated
Operating Class as shown in Annex E."
::= { dot11WirelessMGTEventEntry 24 }
dot11WirelessMGTEventPeerSTATxPower OBJECT-TYPE
SYNTAX Integer32 (-128..127)
MAX-ACCESS read-only
STATUS current
DESCRIPTION
"This attribute indicates the STA transmit power used for the Peer-to-Peer
link. The STA Tx Power field indicates the target transmit power at the
antenna in dBm with a tolerance of +/-5 dB for the lowest basic rate of
the reporting STA. A value of -128 indicates that the value is unknown."
::= { dot11WirelessMGTEventEntry 25 }
dot11WirelessMGTEventPeerConnectionTime OBJECT-TYPE
SYNTAX Unsigned32 (0..16777215)
UNITS "seconds"
MAX-ACCESS read-only
STATUS current
DESCRIPTION
"This attribute indicates a value representing the connection time for the
reported Peer-to-Peer event. If the Peer Status is 0, this field indicates
the duration of the Direct Link. If the Peer Status is 1, this field indicates
the time difference from the time the Direct Link was established to
the time at which the reporting STA generated the event report. If the
Peer Status is 2, this field indicates the duration of the IBSS membership.
If the Peer Status is 3, this field indicates the time difference
from the time the STA joined the IBSS to the time at which the reporting
STA generated the event report. See 10.23.2.4."
::= { dot11WirelessMGTEventEntry 26 }
dot11WirelessMGTEventPeerPeerStatus OBJECT-TYPE
SYNTAX Unsigned32 (0..255)
MAX-ACCESS read-only
STATUS current
DESCRIPTION
"This attribute indicates the Peer link connection status as indicated in
Table 8-139. See 8.4.2.70.4."
::= { dot11WirelessMGTEventEntry 27 }
dot11WirelessMGTEventWNMLog OBJECT-TYPE
SYNTAX OCTET STRING (SIZE(0..2284))
MAX-ACCESS read-only
STATUS current
DESCRIPTION
"This attribute contains the entire syslog message, consisting of the PRI,
HEADER, and MSG portion of a WNM Log message as described in IETF RFC
3164-2001. The TAG field of the MSG portion of the message is a 17 octet
string containing the ASCII representation of the STA MAC address using
hexadecimal notation with colons between octets. The octet containing the
individual/group bit occurs last, and that bit is in the least significant
position within that octet. See 10.23.2.5."
::= { dot11WirelessMGTEventEntry 28 }
-- ********************************************************************
-- * End of dot11WirelessMGTEvent TABLE
-- ********************************************************************
-- ********************************************************************
-- * Wireless Network Management Interface MIB
-- ********************************************************************
dot11WirelessNetworkManagement OBJECT IDENTIFIER ::= { dot11smt 22 }
-- ********************************************************************
-- * Wireless network management requests
-- ********************************************************************
dot11WNMRequest OBJECT IDENTIFIER ::= { dot11WirelessNetworkManagement 1 }
-- ********************************************************************
-- * dot11WNMRequest TABLE
-- ********************************************************************
dot11WNMRequestNextIndex OBJECT-TYPE
SYNTAX Unsigned32(0..4294967295)
MAX-ACCESS read-only
STATUS current
DESCRIPTION
"This is a status variable.
It is written by the SME when able to accept a new request.
Identifies a hint for the next value of dot11WNMRqstIndex to be used in a
row creation attempt for dot11WNMRequestTable. If no new rows can be created
for some reason, such as memory, processing requirements, etc, the
SME shall set this attribute to 0. It shall update this attribute to a
proper value other than 0 as soon as it is capable of receiving new measurement
requests. The nextIndex is not necessarily sequential nor monotonically
increasing."
::= { dot11WNMRequest 1 }
dot11WNMRequestTable OBJECT-TYPE
SYNTAX SEQUENCE OF Dot11WNMRequestEntry
MAX-ACCESS not-accessible
STATUS current
DESCRIPTION
"This group contains the current list of requests for WNM reports to be
issued and have been issued until removed. A network manager adds a WNM
request by creating a row with createAndWait row status and then filling
in the request parameters/attributes. The request becomes active to be
issued when the row status is set to Active. The columnar objects or
attributes other than the rowStatus shall not be written if the rowStatus
is Active. The request rows can be deleted, if commanded by a network manager
via changing the value of dot11WNMRqstRowStatus to Destroy. This may
leave orphaned rows if a manager crashes and forgets which rows are being
used by it. One recommended way to manage orphaned or finished rows is to
delete rows if their dot11WNMRqstRowStatus remains other than Active for
longer than a period (recommend at least 5 minutes, IETF RFC 2579). Or
another recommended way is to delete older rows as needed based on their
dot11WNMRqstTimeStamp values. This can be done by the agent as well as the
manager."
::= { dot11WNMRequest 2 }
dot11WNMRequestEntry OBJECT-TYPE
SYNTAX Dot11WNMRequestEntry
MAX-ACCESS not-accessible
STATUS current
DESCRIPTION
"An entry in the dot11WNMRequestTable Indexed by dot11WNMRqstIndex."
INDEX { dot11WNMRqstIndex }
::= { dot11WNMRequestTable 1 }
Dot11WNMRequestEntry ::=
SEQUENCE {
dot11WNMRqstIndex Unsigned32,
dot11WNMRqstRowStatus RowStatus,
dot11WNMRqstToken OCTET STRING,
dot11WNMRqstIfIndex InterfaceIndex,
dot11WNMRqstType INTEGER,
dot11WNMRqstTargetAdd MacAddress,
dot11WNMRqstTimeStamp TimeTicks,
dot11WNMRqstRndInterval Unsigned32,
dot11WNMRqstDuration Unsigned32,
dot11WNMRqstMcstGroup MacAddress,
dot11WNMRqstMcstTrigCon OCTET STRING,
dot11WNMRqstMcstTrigInactivityTimeout Unsigned32,
dot11WNMRqstMcstTrigReactDelay Unsigned32,
dot11WNMRqstLCRRqstSubject INTEGER,
dot11WNMRqstLCRIntervalUnits INTEGER,
dot11WNMRqstLCRServiceInterval Unsigned32,
dot11WNMRqstLIRRqstSubject INTEGER,
dot11WNMRqstLIRIntervalUnits INTEGER,
dot11WNMRqstLIRServiceInterval Unsigned32,
dot11WNMRqstEventToken Unsigned32,
dot11WNMRqstEventType INTEGER,
dot11WNMRqstEventResponseLimit Unsigned32,
dot11WNMRqstEventTargetBssid MacAddress,
dot11WNMRqstEventSourceBssid MacAddress,
dot11WNMRqstEventTransitTimeThresh Unsigned32,
dot11WNMRqstEventTransitMatchValue OCTET STRING,
dot11WNMRqstEventFreqTransitCountThresh Unsigned32,
dot11WNMRqstEventFreqTransitInterval Unsigned32,
dot11WNMRqstEventRsnaAuthType OCTET STRING,
dot11WNMRqstEapType Unsigned32,
dot11WNMRqstEapVendorId OCTET STRING,
dot11WNMRqstEapVendorType OCTET STRING,
dot11WNMRqstEventRsnaMatchValue OCTET STRING,
dot11WNMRqstEventPeerMacAddress MacAddress,
dot11WNMRqstOperatingClass Unsigned32,
dot11WNMRqstChanNumber Unsigned32,
dot11WNMRqstDiagToken Unsigned32,
dot11WNMRqstDiagType INTEGER,
dot11WNMRqstDiagTimeout Unsigned32,
dot11WNMRqstDiagBssid MacAddress,
dot11WNMRqstDiagProfileId Unsigned32,
dot11WNMRqstDiagCredentials INTEGER,
dot11WNMRqstLocConfigLocIndParams OCTET STRING,
dot11WNMRqstLocConfigChanList OCTET STRING,
dot11WNMRqstLocConfigBcastRate Unsigned32,
dot11WNMRqstLocConfigOptions OCTET STRING,
dot11WNMRqstBssTransitQueryReason INTEGER,
dot11WNMRqstBssTransitReqMode OCTET STRING,
dot11WNMRqstBssTransitDisocTimer Unsigned32,
dot11WNMRqstBssTransitSessInfoURL OCTET STRING,
dot11WNMRqstBssTransitCandidateList OCTET STRING,
dot11WNMRqstColocInterfAutoEnable TruthValue,
dot11WNMRqstColocInterfRptTimeout Unsigned32,
dot11WNMRqstVendorSpecific OCTET STRING,
dot11WNMRqstDestinationURI OCTET STRING
}
dot11WNMRqstIndex OBJECT-TYPE
SYNTAX Unsigned32
MAX-ACCESS not-accessible
STATUS current
DESCRIPTION
"Index for WNM Request elements in dot11WNMRequestTable, greater than 0."
::= { dot11WNMRequestEntry 1 }
dot11WNMRqstRowStatus OBJECT-TYPE
SYNTAX RowStatus
MAX-ACCESS read-create
STATUS current
DESCRIPTION
"This is a control variable.
It is written by an external management entity when requesting a measurement,
and by the SME when accepting a management request.
The Row Status column of the current row, used for tracking status of an
individual request. When this attribute is set to Active, AND a measurement
request can be unambiguously created based on the parameters in the
row, then the MLME may proceed to issue the request to its intended targets
when appropriate. If not, this attribute may be set to Not-ready
immediately to indicate parametric errors. However, it is the network managers
responsibility to correct the error. If the request is successfully issued
to the target STA, then the rowStatus is set to notInService."
::= { dot11WNMRequestEntry 2 }
dot11WNMRqstToken OBJECT-TYPE
SYNTAX OCTET STRING
MAX-ACCESS read-create
STATUS current
DESCRIPTION
"This is a control variable.
It is written by an external management entity when the table entry is
created, i.e., when requesting a measurement. Changes take effect when
dot11RMRqstRowStatus is set to Active.
This attribute indicates a unique string to identify this request. To
guarantee the uniqueness of this token across multiple network managers,
it is recommended that this token be prefixed with the IP address of the
network manager creating this row. This token is not necessarily equivalent
to the measurement tokens in WNM request frames."
::= { dot11WNMRequestEntry 3 }
dot11WNMRqstIfIndex OBJECT-TYPE
SYNTAX InterfaceIndex
MAX-ACCESS read-create
STATUS current
DESCRIPTION
"The ifIndex for this row of WNM Request to be issued on."
::= { dot11WNMRequestEntry 4 }
dot11WNMRqstType OBJECT-TYPE
SYNTAX INTEGER {
mcastDiagnostics(0),
locationCivic(1),
locationIdentifier(2),
event(3),
dignostic(4),
locationConfiguration(5),
bssTransitionQuery(6),
bssTransitionRqst(7),
fms(8),
colocInterference(9)
}
MAX-ACCESS read-create
STATUS current
DESCRIPTION
"This is a control variable.
It is written by an external management entity when making a management
request. Changes take effect when dot11WNMRqstRowStatus is set to Active.
This attribute indicates the request type of this WNM request row."
::= { dot11WNMRequestEntry 5 }
dot11WNMRqstTargetAdd OBJECT-TYPE
SYNTAX MacAddress
MAX-ACCESS read-create
STATUS current
DESCRIPTION
"This is a control variable.
It is written by an external management entity when making a management
request. Changes take effect when dot11WNMRqstRowStatus is set to Active.
The MAC address of STA for this row of WNM Request is to be issued to. If
this attribute matches the MAC address of the dot11WNMRqstIfIndex, then
measurement request is for this STA itself to carry out."
::= { dot11WNMRequestEntry 6 }
dot11WNMRqstTimeStamp OBJECT-TYPE
SYNTAX TimeTicks
MAX-ACCESS read-only
STATUS current
DESCRIPTION
"This is a control variable.
It is written by an external management entity when making a management
request. Changes take effect when dot11WNMRqstRowStatus is set to Active.
This attribute indicates the SysUpTime Value the last time when the
dot11WNMRqstRowStatus is set to active or when this row is created the
first time. This attribute shall be set by this STA or AP automatically,
not by an SNMP manager."
::= { dot11WNMRequestEntry 7 }
dot11WNMRqstRndInterval OBJECT-TYPE
SYNTAX Unsigned32
UNITS "TUs"
MAX-ACCESS read-create
STATUS current
DESCRIPTION
"This is a control variable.
It is written by an external management entity when making a management
request. Changes take effect when dot11WNMRqstRowStatus is set to Active.
This attribute indicates the upper bound of the random delay to be used
prior to making the measurement, expressed in units of TUs. See 10.11.3."
DEFVAL { 0 }
::= { dot11WNMRequestEntry 8 }
dot11WNMRqstDuration OBJECT-TYPE
SYNTAX Unsigned32
UNITS "TUs"
MAX-ACCESS read-create
STATUS current
DESCRIPTION
"This is a control variable.
It is written by an external management entity when making a management
request. Changes take effect when dot11WNMRqstRowStatus is set to Active.
This attribute indicates the preferred or mandatory measurement duration
for this Measurement Request."
DEFVAL { 0 }
::= { dot11WNMRequestEntry 9 }
dot11WNMRqstMcstGroup OBJECT-TYPE
SYNTAX MacAddress
MAX-ACCESS read-create
STATUS current
DESCRIPTION
"This is a control variable.
It is written by an external management entity when making a management
request. Changes take effect when dot11WNMRqstRowStatus is set to Active.
Multicast Group address indicates the MAC address of the multicast group
for which diagnostics are requested. The BSSID shall be set to the wildcard
BSSID when the measurement is to be performed on any muliticast group
on the operating channel. This attribute is only valid if the
dot11WNMRqstType is 10, indicating a multicast diagnostic request, and is
ignored otherwise."
DEFVAL { 'FFFFFFFFFFFF'H }
::= { dot11WNMRequestEntry 10 }
dot11WNMRqstMcstTrigCon OBJECT-TYPE
SYNTAX OCTET STRING (SIZE(1))
MAX-ACCESS read-create
STATUS current
DESCRIPTION
"This is a control variable.
It is written by an external management entity when making a management
request. Changes take effect when dot11WNMRqstRowStatus is set to Active.
This attribute indicates the trigger condition for the Multicast Diagnostic
request."
::= { dot11WNMRequestEntry 11 }
dot11WNMRqstMcstTrigInactivityTimeout OBJECT-TYPE
SYNTAX Unsigned32 (1..255)
UNITS "100 TUs"
MAX-ACCESS read-create
STATUS current
DESCRIPTION
"This is a control variable.
It is written by an external management entity when making a management
request. Changes take effect when dot11WNMRqstRowStatus is set to Active.
This attribute indicates the time interval value in units of 100 TU to be
use as the threshold value for Trigger Inactivity Timeout trigger condition."
::= { dot11WNMRequestEntry 12 }
dot11WNMRqstMcstTrigReactDelay OBJECT-TYPE
SYNTAX Unsigned32 (1..255)
UNITS "100 TUs"
MAX-ACCESS read-create
STATUS current
DESCRIPTION
"This is a control variable.
It is written by an external management entity when making a management
request. Changes take effect when dot11WNMRqstRowStatus is set to Active.
This attribute indicates the time interval value in units of 100 TU during
which a measuring STA does not generate further Multicast Triggered
Reports after a trigger condition has been met."
::= { dot11WNMRequestEntry 13 }
dot11WNMRqstLCRRqstSubject OBJECT-TYPE
SYNTAX INTEGER {
local(0),
remote(1)
}
MAX-ACCESS read-create
STATUS current
DESCRIPTION
"This is a control variable.
It is written by an external management entity when making a management
request. Changes take effect when dot11WNMRqstRowStatus is set to Active.
The attribute indicates the subject of the Location Civic Request."
DEFVAL { 0 }
::= { dot11WNMRequestEntry 14 }
dot11WNMRqstLCRIntervalUnits OBJECT-TYPE
SYNTAX INTEGER {
seconds(0),
minutes(1),
hours(2)
}
MAX-ACCESS read-create
STATUS current
DESCRIPTION
"This is a control variable.
It is written by an external management entity when making a management
request. Changes take effect when dot11WNMRqstRowStatus is set to Active.
This attribute indicates the units used in the Location Civic Request Service
Interval."
::= { dot11WNMRequestEntry 15 }
dot11WNMRqstLCRServiceInterval OBJECT-TYPE
SYNTAX Unsigned32 (0..65535)
MAX-ACCESS read-create
STATUS current
DESCRIPTION
"This is a control variable.
It is written by an external management entity when making a management
request. Changes take effect when dot11WNMRqstRowStatus is set to Active.
This attribute indicates the time interval, expressed in the units indicated
in the Location Civic Request Service Interval Units field, at which
the STA requests to receive Location Civic Reports. A Location Civic
Request Service Interval of 0 indicates that only a single Location Civic
Report is requested."
::= { dot11WNMRequestEntry 16 }
dot11WNMRqstLIRRqstSubject OBJECT-TYPE
SYNTAX INTEGER {
local(0),
remote(1)
}
MAX-ACCESS read-create
STATUS current
DESCRIPTION
"This is a control variable.
It is written by an external management entity when making a management
request. Changes take effect when dot11WNMRqstRowStatus is set to Active.
The attribute indicates the subject of the Location Identifier Request."
DEFVAL { 0 }
::= { dot11WNMRequestEntry 17 }
dot11WNMRqstLIRIntervalUnits OBJECT-TYPE
SYNTAX INTEGER {
seconds(0),
minutes(1),
hours(2)
}
MAX-ACCESS read-create
STATUS current
DESCRIPTION
"This is a control variable.
It is written by an external management entity when making a management
request. Changes take effect when dot11WNMRqstRowStatus is set to Active.
This attribute indicates the units used in the Location Identifier Request
Service Interval."
::= { dot11WNMRequestEntry 18 }
dot11WNMRqstLIRServiceInterval OBJECT-TYPE
SYNTAX Unsigned32 (0..65535)
MAX-ACCESS read-create
STATUS current
DESCRIPTION
"This is a control variable.
It is written by an external management entity when making a management
request. Changes take effect when dot11WNMRqstRowStatus is set to Active.
This attribute indicates the time interval, expressed in the units indicated
in the Location Identifier Request Interval Units field, at which
the STA requests to receive Location Identifier Reports. A Location Identifier
Request Service Interval of 0 indicates that only a single Location
Identifier Report is requested."
::= { dot11WNMRequestEntry 19 }
dot11WNMRqstEventToken OBJECT-TYPE
SYNTAX Unsigned32 (1..255)
MAX-ACCESS read-create
STATUS current
DESCRIPTION
"This is a control variable.
It is written by an external management entity when making a management
request. Changes take effect when dot11WNMRqstRowStatus is set to Active.
This attribute indicates a unique string to identify this request."
::= { dot11WNMRequestEntry 20 }
dot11WNMRqstEventType OBJECT-TYPE
SYNTAX INTEGER {
transition(0),
rsna(1),
peerToPeer(2),
wnmLog(3),
vendorSpecific(221)
}
MAX-ACCESS read-create
STATUS current
DESCRIPTION
"This is a control variable.
It is written by an external management entity when making a management
request. Changes take effect when dot11WNMRqstRowStatus is set to Active.
This attribute indicates the request type of this WNM Event request."
::= { dot11WNMRequestEntry 21 }
dot11WNMRqstEventResponseLimit OBJECT-TYPE
SYNTAX Unsigned32 (0..255)
MAX-ACCESS read-create
STATUS current
DESCRIPTION
"This is a control variable.
It is written by an external management entity when making a management
request. Changes take effect when dot11WNMRqstRowStatus is set to Active.
This attribute indicates the maximum number of requested Event Reports to
be included in the Event Report element. A value of 0 indicates that no
limit is set on the number of Event Reports to be included in the Event
Report element."
::= { dot11WNMRequestEntry 22 }
dot11WNMRqstEventTargetBssid OBJECT-TYPE
SYNTAX MacAddress
MAX-ACCESS read-create
STATUS current
DESCRIPTION
"This is a control variable.
It is written by an external management entity when making a management
request. Changes take effect when dot11WNMRqstRowStatus is set to Active.
This attribute is used to request that a Transition or RSNA Event Report
includes the event entry when the target BSSID is equal to the indicated
BSSID. A transition event is a STA movement or attempted movement from one
BSS (the source BSS) in one ESS to another BSS (the target BSS) within the
same ESS. The BSSID shall be set to the wildcard BSSID when the transitions
to any BSSID is requested."
DEFVAL { 'FFFFFFFFFFFF'H }
::= { dot11WNMRequestEntry 23 }
dot11WNMRqstEventSourceBssid OBJECT-TYPE
SYNTAX MacAddress
MAX-ACCESS read-create
STATUS current
DESCRIPTION
"This is a control variable.
It is written by an external management entity when making a management
request. Changes take effect when dot11WNMRqstRowStatus is set to Active.
This attribute is used to request that a Transition Event Report includes
the transition event entry when the source BSSID is equal to the indicated
BSSID. A transition event is a STA movement or attempted movement from one
BSS (the source BSS) in one ESS to another BSS (the target BSS) within the
same ESS. The BSSID shall be set to the wildcard BSSID when the transitions
from any BSSID is requested."
DEFVAL { 'FFFFFFFFFFFF'H }
::= { dot11WNMRequestEntry 24 }
dot11WNMRqstEventTransitTimeThresh OBJECT-TYPE
SYNTAX Unsigned32 (0..65535)
UNITS "TUs"
MAX-ACCESS read-create
STATUS current
DESCRIPTION
"This is a control variable.
It is written by an external management entity when making a management
request. Changes take effect when dot11WNMRqstRowStatus is set to Active.
This attribute indicates a value representing the transition time to be
used as the threshold value for the Transition Time condition in TUs. The
Transition Time is defined in 10.23.2.2"
::= { dot11WNMRequestEntry 25 }
dot11WNMRqstEventTransitMatchValue OBJECT-TYPE
SYNTAX OCTET STRING (SIZE(1))
MAX-ACCESS read-create
STATUS current
DESCRIPTION
"This is a control variable.
It is written by an external management entity when making a management
request. Changes take effect when dot11WNMRqstRowStatus is set to Active.
This attribute indicates a request for the specified transition results
that match the bit descriptions of this field. b0 indicates match when
transition is successful. b1 indicates match when transition fails."
::= { dot11WNMRequestEntry 26 }
dot11WNMRqstEventFreqTransitCountThresh OBJECT-TYPE
SYNTAX Unsigned32 (0..255)
MAX-ACCESS read-create
STATUS current
DESCRIPTION
"This is a control variable.
It is written by an external management entity when making a management
request. Changes take effect when dot11WNMRqstRowStatus is set to Active.
This attribute indicates the minimum number of matching transitions
detected in the measurement duration to generate a Transition Event
Report."
::= { dot11WNMRequestEntry 27 }
dot11WNMRqstEventFreqTransitInterval OBJECT-TYPE
SYNTAX Unsigned32 (0..65535)
UNITS "TUs"
MAX-ACCESS read-create
STATUS current
DESCRIPTION
"This is a control variable.
It is written by an external management entity when making a management
request. Changes take effect when dot11WNMRqstRowStatus is set to Active.
This attribute indicates the sliding window time interval, in TUs, during
which the STA detects matching transitions to determine if the Frequent
Transition Count Threshold is exceeded in order to generate a Transition
Event Report."
::= { dot11WNMRequestEntry 28 }
dot11WNMRqstEventRsnaAuthType OBJECT-TYPE
SYNTAX OCTET STRING (SIZE(4))
MAX-ACCESS read-create
STATUS current
DESCRIPTION
"This is a control variable.
It is written by an external management entity when making a management
request. Changes take effect when dot11WNMRqstRowStatus is set to Active.
This attribute is used to request that an RSNA Event Report include the
event entry when its RSNA Authentication Type matches the indicated RSNA
authentication type value."
::= { dot11WNMRequestEntry 29 }
dot11WNMRqstEapType OBJECT-TYPE
SYNTAX Unsigned32 (0..255)
MAX-ACCESS read-create
STATUS current
DESCRIPTION
"This is a control variable.
It is written by an external management entity when making a management
request. Changes take effect when dot11WNMRqstRowStatus is set to Active.
This attribute is used to request that an RSNA Event Report include the
event entry when its EAP Type matches the indicated EAP type value. Valid
EAP Type numbers are assigned by IANA and are defined at http://
www.iana.org/assignments/eap-numbers."
::= { dot11WNMRequestEntry 30 }
dot11WNMRqstEapVendorId OBJECT-TYPE
SYNTAX OCTET STRING (SIZE(0..3))
MAX-ACCESS read-create
STATUS current
DESCRIPTION
"This is a control variable.
It is written by an external management entity when making a management
request. Changes take effect when dot11WNMRqstRowStatus is set to Active.
This attribute is used to request that an RSNA Event Report include the
event entry when its EAP Vendor ID matches the indicated vendor ID value.
The EAP Vendor ID field is included when the EAP Type field is set to 254,
and is excluded otherwise."
::= { dot11WNMRequestEntry 31 }
dot11WNMRqstEapVendorType OBJECT-TYPE
SYNTAX OCTET STRING (SIZE(0..4))
MAX-ACCESS read-create
STATUS current
DESCRIPTION
"This is a control variable.
It is written by an external management entity when making a management
request. Changes take effect when dot11WNMRqstRowStatus is set to Active.
This attribute is used to request that an RSNA Event Report include the
event entry when its EAP Vendor Type matches the indicated EAP vendor type
value. The EAP Vendor ID field is included when the EAP Type field is set
to 254, and is excluded otherwise."
::= { dot11WNMRequestEntry 32 }
dot11WNMRqstEventRsnaMatchValue OBJECT-TYPE
SYNTAX OCTET STRING (SIZE(1))
MAX-ACCESS read-create
STATUS current
DESCRIPTION
"This is a control variable.
It is written by an external management entity when making a management
request. Changes take effect when dot11WNMRqstRowStatus is set to Active.
This attribute indicates a request for the specified transition results
that match the bit descriptions of this field. b0 (least significant bit)
indicates match when RSNA is successful. b1 indicates match when RSNA
fails."
::= { dot11WNMRequestEntry 33 }
dot11WNMRqstEventPeerMacAddress OBJECT-TYPE
SYNTAX MacAddress
MAX-ACCESS read-create
STATUS current
DESCRIPTION
"This is a control variable.
It is written by an external management entity when making a management
request. Changes take effect when dot11WNMRqstRowStatus is set to Active.
This attribute is used to request that a Peer-to-Peer Event Report
includes the transition event entry when the MAC address of the peer STA
or IBSS BSSID is equal to the indicated MAC address. The MAC address shall
be set to the wildcard BSSID when the transitions from any peer STA or
IBSS BSSID is requested."
DEFVAL { 'FFFFFFFFFFFF'H }
::= { dot11WNMRequestEntry 34 }
dot11WNMRqstOperatingClass OBJECT-TYPE
SYNTAX Unsigned32(1..255)
MAX-ACCESS read-create
STATUS current
DESCRIPTION
"This is a control variable.
It is written by an external management entity when making a management
request. Changes take effect when dot11WNMRqstRowStatus is set to Active.
This attribute indicates the channel set for this WNM request. Country,
Operating Class and Channel Number together specify the channel frequency
and spacing for this measurement request. Valid values of Operating Class
are shown in Annex E."
::= { dot11WNMRequestEntry 35 }
dot11WNMRqstChanNumber OBJECT-TYPE
SYNTAX Unsigned32 (1..255)
MAX-ACCESS read-create
STATUS current
DESCRIPTION
"This is a control variable.
It is written by an external management entity when making a management
request. Changes take effect when dot11WNMRqstRowStatus is set to Active.
This attribute indicates the current operating channel for this WNM
request. The Channel Number is only defined within the indicated Operating
Class as shown in Annex E."
::= { dot11WNMRequestEntry 36 }
dot11WNMRqstDiagToken OBJECT-TYPE
SYNTAX Unsigned32 (1..255)
MAX-ACCESS read-create
STATUS current
DESCRIPTION
"This is a control variable.
It is written by an external management entity when making a management
request. Changes take effect when dot11WNMRqstRowStatus is set to Active.
This attribute indicates a unique string to identify this request."
::= { dot11WNMRequestEntry 37 }
dot11WNMRqstDiagType OBJECT-TYPE
SYNTAX INTEGER {
cancelRequest(0),
manufacturerInfoStaRep(1),
configurationProfile(2),
associationDiag(3),
ieee8021xAuthDiag(4),
vendorSpecific(221)
}
MAX-ACCESS read-create
STATUS current
DESCRIPTION
"This is a control variable.
It is written by an external management entity when making a management
request. Changes take effect when dot11WNMRqstRowStatus is set to Active.
This attribute indicates the request type of this WNM Diagnostic request."
::= { dot11WNMRequestEntry 38 }
dot11WNMRqstDiagTimeout OBJECT-TYPE
SYNTAX Unsigned32 (0..65535)
UNITS "seconds"
MAX-ACCESS read-create
STATUS current
DESCRIPTION
"This is a control variable.
It is written by an external management entity when making a management
request. Changes take effect when dot11WNMRqstRowStatus is set to Active.
This attribute indicates a value representing the time interval after a
Diagnostic Report is generated during which no additional Diagnostic
Reports shall be sent."
::= { dot11WNMRequestEntry 39 }
dot11WNMRqstDiagBssid OBJECT-TYPE
SYNTAX MacAddress
MAX-ACCESS read-create
STATUS current
DESCRIPTION
"This is a control variable.
It is written by an external management entity when making a management
request. Changes take effect when dot11WNMRqstRowStatus is set to Active.
This attribute indicates a request for a Diagnostic Report from the indicated
BSSID. The BSSID shall be set to the wildcard BSSID when diagnostics
from any BSSID is requested."
DEFVAL { 'FFFFFFFFFFFF'H }
::= { dot11WNMRequestEntry 40 }
dot11WNMRqstDiagProfileId OBJECT-TYPE
SYNTAX Unsigned32 (1..255)
MAX-ACCESS read-create
STATUS current
DESCRIPTION
"This is a control variable.
It is written by an external management entity when making a management
request. Changes take effect when dot11WNMRqstRowStatus is set to Active.
This attribute indicates a unique identifier for referencing a configuration
profile available on a device. The value of the identifier can be any
arbitrary value, as long as it is uniquely associated to a single configuration
profile on the device sending the identifier."
::= { dot11WNMRequestEntry 41 }
dot11WNMRqstDiagCredentials OBJECT-TYPE
SYNTAX INTEGER {
none(0),
preSharedKey(1),
usernamePassword(2),
x509Certificate(3),
otherCertificate(4),
oneTimePassword(5),
token(6)
}
MAX-ACCESS read-create
STATUS current
DESCRIPTION
"This is a control variable.
It is written by an external management entity when making a management
request. Changes take effect when dot11WNMRqstRowStatus is set to Active.
This attribute indicates the type of credential used for the IEEE 802.1X
authentication."
::= { dot11WNMRequestEntry 42 }
dot11WNMRqstLocConfigLocIndParams OBJECT-TYPE
SYNTAX OCTET STRING (SIZE(16))
MAX-ACCESS read-create
STATUS current
DESCRIPTION
"This is a control variable.
It is written by an external management entity when making a management
request. Changes take effect when dot11WNMRqstRowStatus is set to Active.
This attribute indicates STA Location reporting characteristics. The format
of these Location Indication Parameters are detailed in 8.4.2.73.2."
::= { dot11WNMRequestEntry 43 }
dot11WNMRqstLocConfigChanList OBJECT-TYPE
SYNTAX OCTET STRING (SIZE(0..252))
MAX-ACCESS read-create
STATUS current
DESCRIPTION
"This is a control variable.
It is written by an external management entity when making a management
request. Changes take effect when dot11WNMRqstRowStatus is set to Active.
This attribute lists location reporting channel information for this Location
Configuration request. The default value is null. Each pair of octets
indicates a different operating class and channel number for this request.
The detailed format for this list of channels is described in 8.4.2.73.3."
DEFVAL { ''H }
::= { dot11WNMRequestEntry 44 }
dot11WNMRqstLocConfigBcastRate OBJECT-TYPE
SYNTAX Unsigned32 (0..65535)
UNITS "0.5Mb/s"
MAX-ACCESS read-create
STATUS current
DESCRIPTION
"This is a control variable.
It is written by an external management entity when making a management
request. Changes take effect when dot11WNMRqstRowStatus is set to Active.
This attribute indicates the target data rate, in 0.5Mb/s units, at which
the STA transmits Location Track Notification frames. A value of 0 indicates
the STA transmits Location Track Notification frames at a rate chosen
by the STA transmitting the Location Track Notification frames."
::= { dot11WNMRequestEntry 45 }
dot11WNMRqstLocConfigOptions OBJECT-TYPE
SYNTAX OCTET STRING (SIZE(0..255))
MAX-ACCESS read-create
STATUS current
DESCRIPTION
"This is a control variable.
It is written by an external management entity when making a management
request. Changes take effect when dot11WNMRqstRowStatus is set to Active.
This attribute indicates the location track indication options used; see
8.4.2.73.9."
DEFVAL { ''H }
::= { dot11WNMRequestEntry 46 }
dot11WNMRqstBssTransitQueryReason OBJECT-TYPE
SYNTAX INTEGER {
unspecified(0),
excessiveFrameLossRatesPoorConditions(1),
excessiveDelayForCurrentTrafficStreams(2),
insufficientQosCapacityForCurrentTrafficStreams(3),
firstAssociationToEss(4),
loadBalancing(5),
betterApFound(6),
deauthenticatedDisassociatedFromPreviousAp(7),
apFailedIeee8021XEapAuthentication(8),
apFailed4wayHandshake(9),
receivedTooManyReplayCounterFailures(10),
receivedTooManyDataMICFailures(11),
exceededMaxNumberOfRetransmissions(12),
receivedTooManyBroadcastDisassociations(13),
receivedTooManyBroadcastDeauthentications(14),
previousTransitionFailed(15),
lowRSSI(16)
}
MAX-ACCESS read-create
STATUS current
DESCRIPTION
"This is a control variable.
It is written by an external management entity when making a management
request. Changes take effect when dot11WNMRqstRowStatus is set to Active.
This attribute indicates the reason for the BSS Transition Query. The
format for this list of reasons is further detailed in 8.4.2.70.2."
::= { dot11WNMRequestEntry 47 }
dot11WNMRqstBssTransitReqMode OBJECT-TYPE
SYNTAX OCTET STRING (SIZE(1))
MAX-ACCESS read-create
STATUS current
DESCRIPTION
"This is a control variable.
It is written by an external management entity when making a management
request. Changes take effect when dot11WNMRqstRowStatus is set to Active.
This attribute indicates the type of BSS request transition. b0 (least
significant bit) indicates the Preferred Candidate list is included in
this frame. b1 indicates an abridged format for all BSSIDs not listed in
this frame. b2 indicates that the STA will be disassociated for the current
AP. b3 indicates the BSS is shutting down and that the STA will be
disassociated. b4 indicates that the will be disassociated from the ESS.
The format for this field is detailed in 8.5.14.9."
::= { dot11WNMRequestEntry 48 }
dot11WNMRqstBssTransitDisocTimer OBJECT-TYPE
SYNTAX Unsigned32 (0..65535)
UNITS "TBTTs"
MAX-ACCESS read-create
STATUS current
DESCRIPTION
"This is a control variable.
It is written by an external management entity when making a management
request. Changes take effect when dot11WNMRqstRowStatus is set to Active.
This attribute indicates the number of beacon transmission times (TBTTs)
until the serving AP sends a Disassociation frame to this STA. The value 0
indicates unknown. If the Disassociation Imminent bit of the Request Mode
field is set to 0, this field is ignored."
::= { dot11WNMRequestEntry 49 }
dot11WNMRqstBssTransitSessInfoURL OBJECT-TYPE
SYNTAX OCTET STRING
MAX-ACCESS read-create
STATUS current
DESCRIPTION
"This is a control variable.
It is written by an external management entity when making a management
request. Changes take effect when dot11WNMRqstRowStatus is set to Active.
This attribute contains a variable-length field formatted in accordance
with IETF RFC 3986-2005."
::= { dot11WNMRequestEntry 50 }
dot11WNMRqstBssTransitCandidateList OBJECT-TYPE
SYNTAX OCTET STRING (SIZE(0..2304))
MAX-ACCESS read-create
STATUS current
DESCRIPTION
"This is a control variable.
It is written by an external management entity when making a management
request. Changes take effect when dot11WNMRqstRowStatus is set to Active.
This attribute lists one or more Neighbor Report elements described in
8.4.2.39. If the STA has no Transition Candidate information in response
to the BSS Transition Management Query frame, the candidate list is null.
"
::= { dot11WNMRequestEntry 51 }
dot11WNMRqstColocInterfAutoEnable OBJECT-TYPE
SYNTAX TruthValue
MAX-ACCESS read-create
STATUS current
DESCRIPTION
"This is a control variable.
It is written by an external management entity when making a management
request. Changes take effect when dot11WNMRqstRowStatus is set to Active.
This attribute, when true, indicates that the requesting STA requests the
receiving STA to send the Collocated Interference Response frames periodically
with the Report Period interval, as defined in 8.5.14.13, or when
the STA detects a change in the collocated interference."
::= { dot11WNMRequestEntry 52 }
dot11WNMRqstColocInterfRptTimeout OBJECT-TYPE
SYNTAX Unsigned32 (0..127)
UNITS "100 TUs"
MAX-ACCESS read-create
STATUS current
DESCRIPTION
"This is a control variable.
It is written by an external management entity when making a management
request. Changes take effect when dot11WNMRqstRowStatus is set to Active.
This attribute indicates the minimum duration between two consecutive Collocated
Interference Response frames from the reporting STA."
::= { dot11WNMRequestEntry 53 }
dot11WNMRqstVendorSpecific OBJECT-TYPE
SYNTAX OCTET STRING (SIZE(0..255))
MAX-ACCESS read-create
STATUS current
DESCRIPTION
"This is a control variable.
It is written by an external management entity when making a management
request. Changes take effect when dot11WNMRqstRowStatus is set to Active.
This attribute provides an envelope for any optional vendor specific subelements
that may be included in a WNM request element. The default value
is null."
DEFVAL { ''H }
::= { dot11WNMRequestEntry 54}
dot11WNMRqstDestinationURI OBJECT-TYPE
SYNTAX OCTET STRING (SIZE(0..253))
MAX-ACCESS read-create
STATUS current
DESCRIPTION
"This is a control variable.
It is written by an external management entity when making a management
request. Changes take effect when dot11WNMRqstRowStatus is set to Active.
This attribute provides the Destination URI which defines an alternate
destination for the WNM request. The alternate destination may be an
internet address on an Ethernet adapter, for example, to be used when the
wireless link to the requesting entity is unavailable or unreliable. The
default value is null."
DEFVAL { ''H }
::= { dot11WNMRequestEntry 55}
-- **********************************************************************
-- * End of dot11WNMRequest TABLE
-- **********************************************************************
-- ********************************************************************
-- * Wireless network management reports:
-- * Report tables contain WNM reports received by this STA or
-- * results of WNM requests performed by this STA.
-- ********************************************************************
dot11WNMReport OBJECT IDENTIFIER ::= { dot11WirelessNetworkManagement 2 }
-- ********************************************************************
-- * dot11WNMVendorSpecificReport TABLE
-- ********************************************************************
dot11WNMVendorSpecificReportTable OBJECT-TYPE
SYNTAX SEQUENCE OF Dot11WNMVendorSpecificReportEntry
MAX-ACCESS not-accessible
STATUS current
DESCRIPTION
"Group contains the current list of Vendor Specific reports that have been
received by the MLME. The report tables shall be maintained as FIFO to
preserve freshness, thus the rows in this table can be deleted for memory
constraints or other implementation constraints determined by the vendor.
New rows shall have different RprtIndex values than those deleted within
the range limitation of the index. One easy way is to monotonically
increase RprtIndex for new reports being written in the table."
::= { dot11WNMReport 1 }
dot11WNMVendorSpecificReportEntry OBJECT-TYPE
SYNTAX Dot11WNMVendorSpecificReportEntry
MAX-ACCESS not-accessible
STATUS current
DESCRIPTION
"An entry in the dot11WNMVendorSpecificReportTable Indexed by
dot11WNMVendorSpecificRprtIndex."
INDEX { dot11WNMVendorSpecificRprtIndex }
::= { dot11WNMVendorSpecificReportTable 1 }
Dot11WNMVendorSpecificReportEntry ::=
SEQUENCE {
dot11WNMVendorSpecificRprtIndex Unsigned32,
dot11WNMVendorSpecificRprtRqstToken OCTET STRING,
dot11WNMVendorSpecificRprtIfIndex InterfaceIndex,
dot11WNMVendorSpecificRprtContent OCTET STRING }
dot11WNMVendorSpecificRprtIndex OBJECT-TYPE
SYNTAX Unsigned32
MAX-ACCESS not-accessible
STATUS current
DESCRIPTION
"Index for Vendor Specific Report elements in
dot11WNMVendorSpecificReportTable, greater than 0."
::= { dot11WNMVendorSpecificReportEntry 1 }
dot11WNMVendorSpecificRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMVendorSpecificReportEntry 2 }
dot11WNMVendorSpecificRprtIfIndex OBJECT-TYPE
SYNTAX InterfaceIndex
MAX-ACCESS read-only
STATUS current
DESCRIPTION
"The ifIndex for this row of WNMVendorSpecific Report has been received
on."
::= { dot11WNMVendorSpecificReportEntry 3 }
dot11WNMVendorSpecificRprtContent OBJECT-TYPE
SYNTAX OCTET STRING (SIZE(0..255))
MAX-ACCESS read-only
STATUS current
DESCRIPTION
"This is a status variable.
It is written by the SME when a management report is completed.
This attribute provides an envelope for all the vendor specific subelements
that may be included in a WNM Vendor Specific request element. The
default value is null."
DEFVAL { ''H }
::= { dot11WNMVendorSpecificReportEntry 4 }
-- ********************************************************************
-- * End of dot11WNMVendorSpecificReport TABLE
-- ********************************************************************
-- ********************************************************************
-- * dot11WNMMulticastDiagnosticReport TABLE
-- ********************************************************************
dot11WNMMulticastDiagnosticReportTable OBJECT-TYPE
SYNTAX SEQUENCE OF Dot11WNMMulticastDiagnosticReportEntry
MAX-ACCESS not-accessible
STATUS current
DESCRIPTION
"Group contains the current list of Multicast Diagnostic reports that have
been received by the MLME. The report tables shall be maintained as FIFO
to preserve freshness, thus the rows in this table can be deleted for memory
constraints or other implementation constraints determined by the vendor.
New rows shall have different RprtIndex values than those deleted
within the range limitation of the index. One easy way is to monotonically
increase RprtIndex for new reports being written in the table."
::= { dot11WNMReport 2 }
dot11WNMMulticastDiagnosticReportEntry OBJECT-TYPE
SYNTAX Dot11WNMMulticastDiagnosticReportEntry
MAX-ACCESS not-accessible
STATUS current
DESCRIPTION
"An entry in the dot11WNMMulticastDiagnosticReportTable Indexed by
dot11WNMMulticastDiagnosticRprtIndex."
INDEX { dot11WNMMulticastDiagnosticRprtIndex }
::= { dot11WNMMulticastDiagnosticReportTable 1 }
Dot11WNMMulticastDiagnosticReportEntry ::=
SEQUENCE {
dot11WNMMulticastDiagnosticRprtIndex Unsigned32,
dot11WNMMulticastDiagnosticRprtRqstToken OCTET STRING,
dot11WNMMulticastDiagnosticRprtIfIndex InterfaceIndex,
dot11WNMMulticastDiagnosticRprtMeasurementTime TSFType,
dot11WNMMulticastDiagnosticRprtDuration Unsigned32,
dot11WNMMulticastDiagnosticRprtMcstGroup MacAddress,
dot11WNMMulticastDiagnosticRprtReason OCTET STRING,
dot11WNMMulticastDiagnosticRprtRcvdMsduCount Unsigned32,
dot11WNMMulticastDiagnosticRprtFirstSeqNumber Unsigned32,
dot11WNMMulticastDiagnosticRprtLastSeqNumber Unsigned32,
dot11WNMMulticastDiagnosticRprtMcstRate Unsigned32 }
dot11WNMMulticastDiagnosticRprtIndex OBJECT-TYPE
SYNTAX Unsigned32
MAX-ACCESS not-accessible
STATUS current
DESCRIPTION
"Index for Multicast Diagnostic Report elements in
dot11WNMMulticastDiagnosticReportTable, greater than 0."
::= { dot11WNMMulticastDiagnosticReportEntry 1 }
dot11WNMMulticastDiagnosticRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMMulticastDiagnosticReportEntry 2 }
dot11WNMMulticastDiagnosticRprtIfIndex OBJECT-TYPE
SYNTAX InterfaceIndex
MAX-ACCESS read-only
STATUS current
DESCRIPTION
"The ifIndex for this row of WNMMulticastDiagnostic Report has been
received on."
::= { dot11WNMMulticastDiagnosticReportEntry 3 }
dot11WNMMulticastDiagnosticRprtMeasurementTime OBJECT-TYPE
SYNTAX TSFType
MAX-ACCESS read-only
STATUS current
DESCRIPTION
"This is a status variable.
It is written by the SME when a management report is completed.
This attribute indicates the value of the STA TSF timer at the time the
measurement started. For a triggered Multicast Diagnostics report, this is
the TSF value at the reporting STA when the trigger condition was met.
When the reason for sending the report is Performance Measurement and the
Multicast Received MSDU Count is nonzero, the Measurement Time field is
set to the value of the STA TSF timer at the time of the first multicast
MSDU received during the measurement interval."
::= { dot11WNMMulticastDiagnosticReportEntry 4 }
dot11WNMMulticastDiagnosticRprtDuration OBJECT-TYPE
SYNTAX Unsigned32
UNITS "TUs"
MAX-ACCESS read-only
STATUS current
DESCRIPTION
"This is a status variable.
It is written by the SME when a management report is completed.
This attribute indicates the period over which the Multicast Diagnostic
Report was generated, expressed in units of TUs."
::= { dot11WNMMulticastDiagnosticReportEntry 5 }
dot11WNMMulticastDiagnosticRprtMcstGroup OBJECT-TYPE
SYNTAX MacAddress
MAX-ACCESS read-only
STATUS current
DESCRIPTION
"This is a status variable.
It is written by the SME when a management report is completed.
Multicast Group address indicates the MAC address of the multicast group
for this report element."
::= { dot11WNMMulticastDiagnosticReportEntry 6 }
dot11WNMMulticastDiagnosticRprtReason OBJECT-TYPE
SYNTAX OCTET STRING (SIZE(1))
MAX-ACCESS read-only
STATUS current
DESCRIPTION
"This is a status variable.
It is written by the SME when a management report is completed.
This attribute indicates the reason why the measuring STA sent the Multicast
Diagnostics report. b0 (least significant bit) indicates Inactivity
Timeout Trigger. b1 indicates the measurement result from the completed
measurement. These are defined further in 8.4.2.24.12."
::= { dot11WNMMulticastDiagnosticReportEntry 7 }
dot11WNMMulticastDiagnosticRprtRcvdMsduCount OBJECT-TYPE
SYNTAX Unsigned32
MAX-ACCESS read-only
STATUS current
DESCRIPTION
"This is a status variable.
It is written by the SME when a management report is completed.
This attribute indicates the total number of multicast MSDUs with the
indicated Multicast MAC Address that were received during the Measurement
Duration. For a triggered multicast diagnostics measurement this is the
total number of MSDUs received between the acceptance of the multicast
diagnostics measurement request and the occurrence of the trigger condition
for MSDUs with the indicated Multicast MAC Address."
::= { dot11WNMMulticastDiagnosticReportEntry 8 }
dot11WNMMulticastDiagnosticRprtFirstSeqNumber OBJECT-TYPE
SYNTAX Unsigned32 (0..65535)
MAX-ACCESS read-only
STATUS current
DESCRIPTION
"This is a status variable.
It is written by the SME when a management report is completed.
This attribute indicates the twelve least significant bits of the First
Sequence Number field. When the LSB of the first octet of the Multicast
MAC address field in the multicast diagnostic request is set to 1, the
twelve LSBs of the First Sequence Number field contain the sequence number
of the first frame received with destination address equal to the value in
the Multicast MAC address field during the measurement period. When the
LSB of the first octet of the Multicast MAC address field in the multicast
diagnostic request is set to 0, the twelve LSBs of the First Sequence Number
field contain the sequence number of the first group addressed frame,
that does not have the broadcast MAC address as its destination, received
during the measurement period. The four most significant bits of the First
Sequence Number field are set to 0. This field is set to 0 if the Multicast
Received MSDU Count is 0."
::= { dot11WNMMulticastDiagnosticReportEntry 9 }
dot11WNMMulticastDiagnosticRprtLastSeqNumber OBJECT-TYPE
SYNTAX Unsigned32 (0..65535)
MAX-ACCESS read-only
STATUS current
DESCRIPTION
"This is a status variable.
It is written by the SME when a management report is completed.
This attribute indicates the twelve least significant bits of the Last
Sequence Number field. When the LSB of the first octet of the Multicast
MAC address field in the multicast diagnostic request is set to 1, the
twelve LSBs of the Last Sequence Number field contain the sequence number
of the last frame received with destination address equal to the value in
the Multicast MAC address field during the measurement period. When the
LSB of the first octet of the Multicast MAC address field in the multicast
diagnostic request is 0, the twelve LSBs of the Last Sequence Number field
contain the sequence number of the last group addressed frame, that does
not have the broadcast MAC address as its destination, received during the
measurement period. The four most significant bits of the Last Sequence
Number field are set to 0. This field is set to 0 if the Multicast
Received MSDU Count is 0."
::= { dot11WNMMulticastDiagnosticReportEntry 10 }
dot11WNMMulticastDiagnosticRprtMcstRate OBJECT-TYPE
SYNTAX Unsigned32 (0..65535)
UNITS "0.5Mb/s"
MAX-ACCESS read-only
STATUS current
DESCRIPTION
"This is a status variable.
It is written by the SME when a management report is completed.
This attribute indicates the highest data rate, in 0.5 Mb/s units, at
which the STA has received a group addressed frame with a valid FCS during
the measurement period.The Multicast Rate field is encoded with the MSB
set to 1 to indicate that the data rate is in the basic rate set, and set
to 0 to indicate that the data rate is not in the basic rate set. The
remaining 15 bit value is multiplied by 0.5 Mb/s to indicate the data
rate. The Multicast Rate field is set to 0 by the STA to indicate that it
has not received a group addressed frame with a valid FCS during the measurement
period."
::= { dot11WNMMulticastDiagnosticReportEntry 11 }
-- ********************************************************************
-- * End of dot11WNMMulticastDiagnosticReport TABLE
-- ********************************************************************
-- ********************************************************************
-- * dot11WNMLocationCivicReport TABLE
-- ********************************************************************
dot11WNMLocationCivicReportTable OBJECT-TYPE
SYNTAX SEQUENCE OF Dot11WNMLocationCivicReportEntry
MAX-ACCESS not-accessible
STATUS current
DESCRIPTION
"Group contains the current list of Location Civic reports that have been
received by the MLME. The report tables shall be maintained as FIFO to
preserve freshness, thus the rows in this table can be deleted for memory
constraints or other implementation constraints determined by the vendor.
New rows shall have different RprtIndex values than those deleted within
the range limitation of the index. One easy way is to monotonically
increase RprtIndex for new reports being written in the table."
::= { dot11WNMReport 3 }
dot11WNMLocationCivicReportEntry OBJECT-TYPE
SYNTAX Dot11WNMLocationCivicReportEntry
MAX-ACCESS not-accessible
STATUS current
DESCRIPTION
"An entry in the dot11WNMLocationCivicReportTable Indexed by
dot11WNMLocationCivicRprtIndex."
INDEX { dot11WNMLocationCivicRprtIndex }
::= { dot11WNMLocationCivicReportTable 1 }
Dot11WNMLocationCivicReportEntry ::=
SEQUENCE {
dot11WNMLocationCivicRprtIndex Unsigned32,
dot11WNMLocationCivicRprtRqstToken OCTET STRING,
dot11WNMLocationCivicRprtIfIndex InterfaceIndex,
dot11WNMLocationCivicRprtCivicLocation OCTET STRING }
dot11WNMLocationCivicRprtIndex OBJECT-TYPE
SYNTAX Unsigned32
MAX-ACCESS not-accessible
STATUS current
DESCRIPTION
"Index for Location Civic Report elements in
dot11WNMLocationCivicReportTable, greater than 0."
::= { dot11WNMLocationCivicReportEntry 1 }
dot11WNMLocationCivicRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMLocationCivicReportEntry 2 }
dot11WNMLocationCivicRprtIfIndex OBJECT-TYPE
SYNTAX InterfaceIndex
MAX-ACCESS read-only
STATUS current
DESCRIPTION
"The ifIndex for this row of WNMLocationCivic Report has been received
on."
::= { dot11WNMLocationCivicReportEntry 3 }
dot11WNMLocationCivicRprtCivicLocation OBJECT-TYPE
SYNTAX OCTET STRING
MAX-ACCESS read-only
STATUS current
DESCRIPTION
"This is a status variable.
It is written by the SME when a management report is completed.
This attribute indicates a variable octet field and contains a list of
civic address elements in TLV format as defined in IETF RFC 4776-2006."
::= { dot11WNMLocationCivicReportEntry 4}
-- ********************************************************************
-- * End of dot11WNMLocationCivicReport TABLE
-- ********************************************************************
-- ********************************************************************
-- * dot11WNMLocationIdentifierReport TABLE
-- ********************************************************************
dot11WNMLocationIdentifierReportTable OBJECT-TYPE
SYNTAX SEQUENCE OF Dot11WNMLocationIdentifierReportEntry
MAX-ACCESS not-accessible
STATUS current
DESCRIPTION
"Group contains the current list of Location Identifier reports that have
been received by the MLME. The report tables shall be maintained as FIFO
to preserve freshness, thus the rows in this table can be deleted for memory
constraints or other implementation constraints determined by the vendor.
New rows shall have different RprtIndex values than those deleted
within the range limitation of the index. One easy way is to monotonically
increase RprtIndex for new reports being written in the table."
::= { dot11WNMReport 4 }
dot11WNMLocationIdentifierReportEntry OBJECT-TYPE
SYNTAX Dot11WNMLocationIdentifierReportEntry
MAX-ACCESS not-accessible
STATUS current
DESCRIPTION
"An entry in the dot11WNMLocationIdentifierReportTable Indexed by
dot11WNMLocationIdentifierRprtIndex."
INDEX { dot11WNMLocationIdentifierRprtIndex }
::= { dot11WNMLocationIdentifierReportTable 1 }
Dot11WNMLocationIdentifierReportEntry ::=
SEQUENCE {
dot11WNMLocationIdentifierRprtIndex Unsigned32,
dot11WNMLocationIdentifierRprtRqstToken OCTET STRING,
dot11WNMLocationIdentifierRprtIfIndex InterfaceIndex,
dot11WNMLocationIdentifierRprtExpirationTSF TSFType,
dot11WNMLocationIdentifierRprtPublicIdUri OCTET STRING }
dot11WNMLocationIdentifierRprtIndex OBJECT-TYPE
SYNTAX Unsigned32
MAX-ACCESS not-accessible
STATUS current
DESCRIPTION
"Index for Location Identifier Report elements in
dot11WNMLocationIdentifierReportTable, greater than 0."
::= { dot11WNMLocationIdentifierReportEntry 1 }
dot11WNMLocationIdentifierRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMLocationIdentifierReportEntry 2 }
dot11WNMLocationIdentifierRprtIfIndex OBJECT-TYPE
SYNTAX InterfaceIndex
MAX-ACCESS read-only
STATUS current
DESCRIPTION
"The ifIndex for this row of WNMLocationIdentifier Report has been
received on."
::= { dot11WNMLocationIdentifierReportEntry 3 }
dot11WNMLocationIdentifierRprtExpirationTSF OBJECT-TYPE
SYNTAX TSFType
MAX-ACCESS read-only
STATUS current
DESCRIPTION
"This is a status variable.
It is written by the SME when a management report is completed.
This attribute indicates the value of the STA TSF timer when the Public
Identifier URI field value is no longer valid. The Expiration TSF field
set to 0 indicates the Public Identifier URI does not expire."
::= { dot11WNMLocationIdentifierReportEntry 4 }
dot11WNMLocationIdentifierRprtPublicIdUri OBJECT-TYPE
SYNTAX OCTET STRING
MAX-ACCESS read-only
STATUS current
DESCRIPTION
"This is a status variable.
It is written by the SME when a management report is completed.
This attribute indicates a value in URI format that points to a location
object. It can be used to return the location value for the requesting
STA. The format of the location value returned when the URI is dereferenced
is dependent on the provider of the URI and is beyond the scope of
this document. The Public Identifier URI confirms the validity of the
location estimate to an external agent when a STA forwards a location
estimate to that agent. The protocol used to query the infrastructure for
a location report based on the Public Identifier URI is beyond the scope
of this standard."
::= { dot11WNMLocationIdentifierReportEntry 5}
-- ********************************************************************
-- * End of dot11WNMLocationIdentifierReport TABLE
-- ********************************************************************
-- ********************************************************************
-- * dot11WNMEventTransitReport TABLE
-- ********************************************************************
dot11WNMEventTransitReportTable OBJECT-TYPE
SYNTAX SEQUENCE OF Dot11WNMEventTransitReportEntry
MAX-ACCESS not-accessible
STATUS current
DESCRIPTION
"Group contains the current list of Transition Event reports that have
been received by the MLME. The report tables shall be maintained as FIFO
to preserve freshness, thus the rows in this table can be deleted for memory
constraints or other implementation constraints determined by the vendor.
New rows shall have different RprtIndex values than those deleted
within the range limitation of the index. One easy way is to monotonically
increase RprtIndex for new reports being written in the table."
::= { dot11WNMReport 5 }
dot11WNMEventTransitReportEntry OBJECT-TYPE
SYNTAX Dot11WNMEventTransitReportEntry
MAX-ACCESS not-accessible
STATUS current
DESCRIPTION
"An entry in the dot11WNMEventTransitReportTable Indexed by
dot11WNMEventTransitRprtIndex."
INDEX { dot11WNMEventTransitRprtIndex }
::= { dot11WNMEventTransitReportTable 1 }
Dot11WNMEventTransitReportEntry ::=
SEQUENCE {
dot11WNMEventTransitRprtIndex Unsigned32,
dot11WNMEventTransitRprtRqstToken OCTET STRING,
dot11WNMEventTransitRprtIfIndex InterfaceIndex,
dot11WNMEventTransitRprtEventStatus INTEGER,
dot11WNMEventTransitRprtEventTSF TSFType,
dot11WNMEventTransitRprtUTCOffset OCTET STRING,
dot11WNMEventTransitRprtTimeError OCTET STRING,
dot11WNMEventTransitRprtSourceBssid MacAddress,
dot11WNMEventTransitRprtTargetBssid MacAddress,
dot11WNMEventTransitRprtTransitTime Unsigned32,
dot11WNMEventTransitRprtTransitReason INTEGER,
dot11WNMEventTransitRprtTransitResult Unsigned32,
dot11WNMEventTransitRprtSourceRCPI Unsigned32,
dot11WNMEventTransitRprtSourceRSNI Unsigned32,
dot11WNMEventTransitRprtTargetRCPI Unsigned32,
dot11WNMEventTransitRprtTargetRSNI Unsigned32 }
dot11WNMEventTransitRprtIndex OBJECT-TYPE
SYNTAX Unsigned32
MAX-ACCESS not-accessible
STATUS current
DESCRIPTION
"Index for Transition Event Report elements in
dot11WNMEventTransitReportTable, greater than 0."
::= { dot11WNMEventTransitReportEntry 1 }
dot11WNMEventTransitRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMEventTransitReportEntry 2 }
dot11WNMEventTransitRprtIfIndex OBJECT-TYPE
SYNTAX InterfaceIndex
MAX-ACCESS read-only
STATUS current
DESCRIPTION
"The ifIndex for this row of WNMEventTransit Report has been received on."
::= { dot11WNMEventTransitReportEntry 3 }
dot11WNMEventTransitRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMEventTransitReportEntry 4 }
dot11WNMEventTransitRprtEventTSF OBJECT-TYPE
SYNTAX TSFType
MAX-ACCESS read-only
STATUS current
DESCRIPTION
"This is a status variable.
It is written by the SME when a management report is completed.
This attribute contains the value of the Event timestamp field."
::= { dot11WNMEventTransitReportEntry 5 }
dot11WNMEventTransitRprtUTCOffset OBJECT-TYPE
SYNTAX OCTET STRING (SIZE(10))
MAX-ACCESS read-only
STATUS current
DESCRIPTION
"This is a status variable.
It is written by the SME when a management report is completed.
This attribute indicates the UTC Offset Time Value optionally included in
the Event Report."
::= { dot11WNMEventTransitReportEntry 6 }
dot11WNMEventTransitRprtTimeError OBJECT-TYPE
SYNTAX OCTET STRING (SIZE(5))
MAX-ACCESS read-only
STATUS current
DESCRIPTION
"This is a status variable.
It is written by the SME when a management report is completed.
This attribute contains the value of the Event Time Error field optionally
included in the Event Report."
::= { dot11WNMEventTransitReportEntry 7 }
dot11WNMEventTransitRprtSourceBssid OBJECT-TYPE
SYNTAX MacAddress
MAX-ACCESS read-only
STATUS current
DESCRIPTION
"This is a status variable.
It is written by the SME when a management report is completed.
This attribute indicates the source BSSID for the reported transition
event."
::= { dot11WNMEventTransitReportEntry 8 }
dot11WNMEventTransitRprtTargetBssid OBJECT-TYPE
SYNTAX MacAddress
MAX-ACCESS read-only
STATUS current
DESCRIPTION
"This is a status variable.
It is written by the SME when a management report is completed.
This attribute indicates the target BSSID for the reported transition
event."
::= { dot11WNMEventTransitReportEntry 9 }
dot11WNMEventTransitRprtTransitTime OBJECT-TYPE
SYNTAX Unsigned32 (0..65535)
UNITS "TUs"
MAX-ACCESS read-only
STATUS current
DESCRIPTION
"This is a status variable.
It is written by the SME when a management report is completed.
This attribute indicates the transition time for the reported transition
event in TUs. The Transition time is defined as the time difference
between the starting time and the ending time of a transition between APs,
even if the transition results in remaining on the same AP. Start and end
times for a transition event are defined in 10.23.2.2"
::= { dot11WNMEventTransitReportEntry 10 }
dot11WNMEventTransitRprtTransitReason OBJECT-TYPE
SYNTAX INTEGER {
unspecified(0),
excessiveFrameLossRatesPoorConditions(1),
excessiveDelayForCurrentTrafficStreams(2),
insufficientQosCapacityForCurrentTrafficStreams(3),
firstAssociationToEss(4),
loadBalancing(5),
betterApFound(6),
deauthenticatedDisassociatedFromPreviousAp(7),
apFailedIeee8021XEapAuthentication(8),
apFailed4wayHandshake(9),
receivedTooManyReplayCounterFailures(10),
receivedTooManyDataMICFailures(11),
exceededMaxNumberOfRetransmissions(12),
receivedTooManyBroadcastDisassociations(13),
receivedTooManyBroadcastDeauthentications(14),
previousTransitionFailed(15),
lowRSSI(16)
}
MAX-ACCESS read-only
STATUS current
DESCRIPTION
"This is a status variable.
It is written by the SME when a management report is completed.
This attribute indicates the reason for the reported BSS Transition event.
The format for this list of reasons is further detailed in 8.4.2.70.2."
::= { dot11WNMEventTransitReportEntry 11 }
dot11WNMEventTransitRprtTransitResult OBJECT-TYPE
SYNTAX Unsigned32(0..65535)
MAX-ACCESS read-only
STATUS current
DESCRIPTION
"This is a status variable.
It is written by the SME when a management report is completed.
This attribute indicates the result of the attempted transition and is set
to one of the status codes specified in Table 8-37 in 8.4.1.9."
::= { dot11WNMEventTransitReportEntry 12 }
dot11WNMEventTransitRprtSourceRCPI OBJECT-TYPE
SYNTAX Unsigned32(0..255)
MAX-ACCESS read-only
STATUS current
DESCRIPTION
"This is a status variable.
It is written by the SME when a management report is completed.
This attribute indicates the received channel power of the most recently
measured frame from the Source BSSID before the STA reassociates to the
Target BSSID. The Source RCPI is a logarithmic function of the received
signal power, as defined in the RCPI measurement subclause for the PHY
Type."
::= { dot11WNMEventTransitReportEntry 13 }
dot11WNMEventTransitRprtSourceRSNI OBJECT-TYPE
SYNTAX Unsigned32(0..255)
MAX-ACCESS read-only
STATUS current
DESCRIPTION
"This is a status variable.
It is written by the SME when a management report is completed.
This attribute indicates the received signal-to-noise indication of the
most recently measured frame from the Source BSSID before the STA reassociates
to the Target BSSID. The Source RSNI is a logarithmic function of
the signal-to-noise ratio, as defined in 8.4.2.43."
::= { dot11WNMEventTransitReportEntry 14 }
dot11WNMEventTransitRprtTargetRCPI OBJECT-TYPE
SYNTAX Unsigned32(0..255)
MAX-ACCESS read-only
STATUS current
DESCRIPTION
"This is a status variable.
It is written by the SME when a management report is completed.
This attribute indicates the received channel power of the first measured
frame just after STA reassociates to the Target BSSID. If association with
target BSSID failed, the Target RCPI field indicates the received channel
power of the most recently measured frame from the Target BSSID. The Target
RCPI is a logarithmic function of the received signal power, as
defined in the RCPI measurement subclause for the PHY Type."
::= { dot11WNMEventTransitReportEntry 15 }
dot11WNMEventTransitRprtTargetRSNI OBJECT-TYPE
SYNTAX Unsigned32(0..255)
MAX-ACCESS read-only
STATUS current
DESCRIPTION
"This is a status variable.
It is written by the SME when a management report is completed.
This attribute indicates the received signal-to-noise indication of the
first measured frame just after STA reassociates to the Target BSSID. If
association with target BSSID failed, the Target RCPI field indicates the
received signal-to-noise indication of the most recently measured frame
from the Target BSSID. The Target RSNI is a logarithmic function of the
signal-to-noise ratio, as defined in 8.4.2.43."
::= { dot11WNMEventTransitReportEntry 16 }
-- ********************************************************************
-- * End of dot11WNMEventTransitReport TABLE
-- ********************************************************************
-- ********************************************************************
-- * dot11WNMEventRsnaReport TABLE
-- ********************************************************************
dot11WNMEventRsnaReportTable OBJECT-TYPE
SYNTAX SEQUENCE OF Dot11WNMEventRsnaReportEntry
MAX-ACCESS not-accessible
STATUS current
DESCRIPTION
"Group contains the current list of RSNA Event reports that have been
received by the MLME. The report tables shall be maintained as FIFO to
preserve freshness, thus the rows in this table can be deleted for memory
constraints or other implementation constraints determined by the vendor.
New rows shall have different RprtIndex values than those deleted within
the range limitation of the index. One easy way is to monotonically
increase RprtIndex for new reports being written in the table."
::= { dot11WNMReport 6 }
dot11WNMEventRsnaReportEntry OBJECT-TYPE
SYNTAX Dot11WNMEventRsnaReportEntry
MAX-ACCESS not-accessible
STATUS current
DESCRIPTION
"An entry in the dot11WNMEventRsnaReportTable Indexed by
dot11WNMEventRsnaRprtIndex."
INDEX { dot11WNMEventRsnaRprtIndex }
::= { dot11WNMEventRsnaReportTable 1 }
Dot11WNMEventRsnaReportEntry ::=
SEQUENCE {
dot11WNMEventRsnaRprtIndex Unsigned32,
dot11WNMEventRsnaRprtRqstToken OCTET STRING,
dot11WNMEventRsnaRprtIfIndex InterfaceIndex,
dot11WNMEventRsnaRprtEventStatus INTEGER,
dot11WNMEventRsnaRprtEventTSF TSFType,
dot11WNMEventRsnaRprtUTCOffset OCTET STRING,
dot11WNMEventRsnaRprtTimeError OCTET STRING,
dot11WNMEventRsnaRprtTargetBssid MacAddress,
dot11WNMEventRsnaRprtAuthType OCTET STRING,
dot11WNMEventRsnaRprtEapMethod OCTET STRING,
dot11WNMEventRsnaRprtResult Unsigned32,
dot11WNMEventRsnaRprtRsnElement OCTET STRING }
dot11WNMEventRsnaRprtIndex OBJECT-TYPE
SYNTAX Unsigned32
MAX-ACCESS not-accessible
STATUS current
DESCRIPTION
"Index for RSNA Event Report elements in dot11WNMEventRsnaReportTable,
greater than 0."
::= { dot11WNMEventRsnaReportEntry 1 }
dot11WNMEventRsnaRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMEventRsnaReportEntry 2 }
dot11WNMEventRsnaRprtIfIndex OBJECT-TYPE
SYNTAX InterfaceIndex
MAX-ACCESS read-only
STATUS current
DESCRIPTION
"The ifIndex for this row of WNMEventRsna Report has been received on."
::= { dot11WNMEventRsnaReportEntry 3 }
dot11WNMEventRsnaRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMEventRsnaReportEntry 4 }
dot11WNMEventRsnaRprtEventTSF OBJECT-TYPE
SYNTAX TSFType
MAX-ACCESS read-only
STATUS current
DESCRIPTION
"This is a status variable.
It is written by the SME when a management report is completed.
This attribute contains the value of the Event timestamp field."
::= { dot11WNMEventRsnaReportEntry 5 }
dot11WNMEventRsnaRprtUTCOffset OBJECT-TYPE
SYNTAX OCTET STRING (SIZE(10))
MAX-ACCESS read-only
STATUS current
DESCRIPTION
"This is a status variable.
It is written by the SME when a management report is completed.
This attribute indicates the UTC Offset Time Value optionally included in
the Event Report."
::= { dot11WNMEventRsnaReportEntry 6 }
dot11WNMEventRsnaRprtTimeError OBJECT-TYPE
SYNTAX OCTET STRING (SIZE(5))
MAX-ACCESS read-only
STATUS current
DESCRIPTION
"This is a status variable.
It is written by the SME when a management report is completed.
This attribute contains the value of the Event Time Error field optionally
included in the Event Report."
::= { dot11WNMEventRsnaReportEntry 7 }
dot11WNMEventRsnaRprtTargetBssid OBJECT-TYPE
SYNTAX MacAddress
MAX-ACCESS read-only
STATUS current
DESCRIPTION
"This is a status variable.
It is written by the SME when a management report is completed.
This attribute indicates the BSSID of the AP accepting the authorization
attempt."
::= { dot11WNMEventRsnaReportEntry 8 }
dot11WNMEventRsnaRprtAuthType OBJECT-TYPE
SYNTAX OCTET STRING (SIZE(4))
MAX-ACCESS read-only
STATUS current
DESCRIPTION
"This is a status variable.
It is written by the SME when a management report is completed.
This attribute indicates the AKM suite, as defined in Table 8-101 in
8.4.2.27.3. The first three octets indicate the OUI. The last octet indicates
the suite type."
::= { dot11WNMEventRsnaReportEntry 9 }
dot11WNMEventRsnaRprtEapMethod OBJECT-TYPE
SYNTAX OCTET STRING (SIZE(1..8))
MAX-ACCESS read-only
STATUS current
DESCRIPTION
"This is a status variable.
It is written by the SME when a management report is completed.
This attribute indicates a value that identifies the EAP Method. When the
Authentication Type field is set to the value of either 00-0F-AC:1
(Authentication negotiated over IEEE 802.1X or using PMKSA caching as
defined in 11.5.9.3) or 00-0F-AC:3 (AKM suite selector for Fast BSS Transition
as defined in 11.6.1.7), the EAP Method field contains the IANA
assigned EAP type defined at http://www.iana.org/assignments/eap-numbers.
The EAP type contains either the legacy type (1 octet) or the expanded
type (1 octet type = 254, 3-octet Vendor ID, 4-octet Vendor-Type). The EAP
Method field is set to 0 otherwise."
::= { dot11WNMEventRsnaReportEntry 10 }
dot11WNMEventRsnaRprtResult OBJECT-TYPE
SYNTAX Unsigned32(0..65535)
MAX-ACCESS read-only
STATUS current
DESCRIPTION
"This is a status variable.
It is written by the SME when a management report is completed.
This attribute indicates the result of the RSNA event and is set to one of
the status codes specified in Table 8-37 in 8.4.1.9."
::= { dot11WNMEventRsnaReportEntry 11 }
dot11WNMEventRsnaRprtRsnElement OBJECT-TYPE
SYNTAX OCTET STRING
MAX-ACCESS read-only
STATUS current
DESCRIPTION
"This is a status variable.
It is written by the SME when a management report is completed.
This attribute contains the entire contents of the negotiated RSNE at the
time of the authentication attempt. The maximum length of the RSNE field
is less than the maximum length of an RSNE, as defined in 8.4.2.27. If the
length of the RSNE included here exceeds the maximum length of the RSNE
field, the RSNE shall be truncated to the maximum length allowed for the
RSNE field."
::= { dot11WNMEventRsnaReportEntry 12 }
-- ********************************************************************
-- * End of dot11WNMEventRsnaReport TABLE
-- ********************************************************************
-- ********************************************************************
-- * dot11WNMEventPeerReport TABLE
-- ********************************************************************
dot11WNMEventPeerReportTable OBJECT-TYPE
SYNTAX SEQUENCE OF Dot11WNMEventPeerReportEntry
MAX-ACCESS not-accessible
STATUS current
DESCRIPTION
"Group contains the current list of Peer-to-Peer Event reports that have
been received by the MLME. The report tables shall be maintained as FIFO
to preserve freshness, thus the rows in this table can be deleted for memory
constraints or other implementation constraints determined by the vendor.
New rows shall have different RprtIndex values than those deleted
within the range limitation of the index. One easy way is to monotonically
increase RprtIndex for new reports being written in the table."
::= { dot11WNMReport 7 }
dot11WNMEventPeerReportEntry OBJECT-TYPE
SYNTAX Dot11WNMEventPeerReportEntry
MAX-ACCESS not-accessible
STATUS current
DESCRIPTION
"An entry in the dot11WNMEventPeerReportTable Indexed by
dot11WNMEventPeerRprtIndex."
INDEX { dot11WNMEventPeerRprtIndex }
::= { dot11WNMEventPeerReportTable 1 }
Dot11WNMEventPeerReportEntry ::=
SEQUENCE {
dot11WNMEventPeerRprtIndex Unsigned32,
dot11WNMEventPeerRprtRqstToken OCTET STRING,
dot11WNMEventPeerRprtIfIndex InterfaceIndex,
dot11WNMEventPeerRprtEventStatus INTEGER,
dot11WNMEventPeerRprtEventTSF TSFType,
dot11WNMEventPeerRprtUTCOffset OCTET STRING,
dot11WNMEventPeerRprtTimeError OCTET STRING,
dot11WNMEventPeerRprtPeerMacAddress MacAddress,
dot11WNMEventPeerRprtOperatingClass Unsigned32,
dot11WNMEventPeerRprtChanNumber Unsigned32,
dot11WNMEventPeerRprtStaTxPower Integer32,
dot11WNMEventPeerRprtConnTime Unsigned32,
dot11WNMEventPeerRprtPeerStatus INTEGER }
dot11WNMEventPeerRprtIndex OBJECT-TYPE
SYNTAX Unsigned32
MAX-ACCESS not-accessible
STATUS current
DESCRIPTION
"Index for Peer-to-Peer Event Report elements in
dot11WNMEventPeerReportTable, greater than 0."
::= { dot11WNMEventPeerReportEntry 1 }
dot11WNMEventPeerRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMEventPeerReportEntry 2 }
dot11WNMEventPeerRprtIfIndex OBJECT-TYPE
SYNTAX InterfaceIndex
MAX-ACCESS read-only
STATUS current
DESCRIPTION
"The ifIndex for this row of WNMEventPeer Report has been received on."
::= { dot11WNMEventPeerReportEntry 3 }
dot11WNMEventPeerRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMEventPeerReportEntry 4 }
dot11WNMEventPeerRprtEventTSF OBJECT-TYPE
SYNTAX TSFType
MAX-ACCESS read-only
STATUS current
DESCRIPTION
"This is a status variable.
It is written by the SME when a management report is completed.
This attribute contains the value of the Event timestamp field."
::= { dot11WNMEventPeerReportEntry 5 }
dot11WNMEventPeerRprtUTCOffset OBJECT-TYPE
SYNTAX OCTET STRING (SIZE(10))
MAX-ACCESS read-only
STATUS current
DESCRIPTION
"This is a status variable.
It is written by the SME when a management report is completed.
This attribute indicates the UTC Offset Time Value optionally included in
the Event Report."
::= { dot11WNMEventPeerReportEntry 6 }
dot11WNMEventPeerRprtTimeError OBJECT-TYPE
SYNTAX OCTET STRING (SIZE(5))
MAX-ACCESS read-only
STATUS current
DESCRIPTION
"This is a status variable.
It is written by the SME when a management report is completed.
This attribute contains the value of the Event Time Error field optionally
included in the Event Report."
::= { dot11WNMEventPeerReportEntry 7 }
dot11WNMEventPeerRprtPeerMacAddress OBJECT-TYPE
SYNTAX MacAddress
MAX-ACCESS read-only
STATUS current
DESCRIPTION
"This is a status variable.
It is written by the SME when a management report is completed.
This attribute indicates the MAC address of the peer STA or IBSS BSSID. If
this event is for a Peer-to-Peer link in an infrastructure BSS, this field
contains the MAC address of the peer STA. If this event is for a Peer-to-
Peer link in an IBSS, this field contains the BSSID of the IBSS."
::= { dot11WNMEventPeerReportEntry 8 }
dot11WNMEventPeerRprtOperatingClass OBJECT-TYPE
SYNTAX Unsigned32(1..255)
MAX-ACCESS read-only
STATUS current
DESCRIPTION
"This is a status variable.
It is written by the SME when a management report is completed.
This attribute indicates the channel set for this Peer-to-Peer Event
report. Country, Operating Class and Channel Number together specify the
channel frequency and spacing for this measurement request. Valid values
of Operating Class as shown in Annex E."
::= { dot11WNMEventPeerReportEntry 9 }
dot11WNMEventPeerRprtChanNumber OBJECT-TYPE
SYNTAX Unsigned32 (1..255)
MAX-ACCESS read-only
STATUS current
DESCRIPTION
"This is a status variable.
It is written by the SME when a management report is completed.
This attribute indicates the current operating channel for this Peer-to-
Peer Event report. The Channel Number is only defined within the indicated
Operating Class as shown in Annex E."
::= { dot11WNMEventPeerReportEntry 10 }
dot11WNMEventPeerRprtStaTxPower OBJECT-TYPE
SYNTAX Integer32 (-128..127)
MAX-ACCESS read-only
STATUS current
DESCRIPTION
"This is a status variable.
It is written by the SME when a management report is completed.
This attribute indicates the STA transmit power used for the Peer-to-Peer
link. The STA Tx Power field indicates the target transmit power at the
antenna in dBm with a tolerance of +/-5dB for the lowest basic rate of the
reporting STA."
::= { dot11WNMEventPeerReportEntry 11 }
dot11WNMEventPeerRprtConnTime OBJECT-TYPE
SYNTAX Unsigned32 (0..16777215)
UNITS "seconds"
MAX-ACCESS read-only
STATUS current
DESCRIPTION
"This is a status variable.
It is written by the SME when a management report is completed.
This attribute indicates a value representing the connection time for the
reported Peer-to-Peer event. If the Peer Status is 0, this field indicates
the duration of the Direct Link. If the Peer Status is 1, this field indicates
the time difference from the time the Direct Link was established to
the time at which the reporting STA generated the event report. If the
Peer Status is 2, this field indicates the duration of the IBSS membership.
If the Peer Status is 3, this field indicates the time difference
from the time the STA joined the IBSS to the time at which the reporting
STA generated the event report. See 10.23.2.4."
::= { dot11WNMEventPeerReportEntry 12 }
dot11WNMEventPeerRprtPeerStatus OBJECT-TYPE
SYNTAX INTEGER {
directLinkTerminated(0),
directLinkActive(1),
ibssMembershipTerminated(2),
ibssMembershipActive(3)
}
MAX-ACCESS read-only
STATUS current
DESCRIPTION
"This is a status variable.
It is written by the SME when a management report is completed.
This attribute indicates the peer link connection status."
::= { dot11WNMEventPeerReportEntry 13 }
-- ********************************************************************
-- * End of dot11WNMEventPeerReport TABLE
-- ********************************************************************
-- ********************************************************************
-- * dot11WNMEventWNMLogReport TABLE
-- ********************************************************************
dot11WNMEventWNMLogReportTable OBJECT-TYPE
SYNTAX SEQUENCE OF Dot11WNMEventWNMLogReportEntry
MAX-ACCESS not-accessible
STATUS current
DESCRIPTION
"Group contains the current list of WNMLog Event reports that have been
received by the MLME. The report tables shall be maintained as FIFO to
preserve freshness, thus the rows in this table can be deleted for memory
constraints or other implementation constraints determined by the vendor.
New rows shall have different RprtIndex values than those deleted within
the range limitation of the index. One easy way is to monotonically
increase RprtIndex for new reports being written in the table."
::= { dot11WNMReport 8 }
dot11WNMEventWNMLogReportEntry OBJECT-TYPE
SYNTAX Dot11WNMEventWNMLogReportEntry
MAX-ACCESS not-accessible
STATUS current
DESCRIPTION
"An entry in the dot11WNMEventWNMLogReportTable Indexed by
dot11WNMEventWNMLogRprtIndex."
INDEX { dot11WNMEventWNMLogRprtIndex }
::= { dot11WNMEventWNMLogReportTable 1 }
Dot11WNMEventWNMLogReportEntry ::=
SEQUENCE {
dot11WNMEventWNMLogRprtIndex Unsigned32,
dot11WNMEventWNMLogRprtRqstToken OCTET STRING,
dot11WNMEventWNMLogRprtIfIndex InterfaceIndex,
dot11WNMEventWNMLogRprtEventStatus INTEGER,
dot11WNMEventWNMLogRprtEventTSF TSFType,
dot11WNMEventWNMLogRprtUTCOffset OCTET STRING,
dot11WNMEventWNMLogRprtTimeError OCTET STRING,
dot11WNMEventWNMLogRprtContent OCTET STRING }
dot11WNMEventWNMLogRprtIndex OBJECT-TYPE
SYNTAX Unsigned32
MAX-ACCESS not-accessible
STATUS current
DESCRIPTION
"Index for WNMLog Event Report elements in dot11WNMEventWNMLogReportTable,
greater than 0."
::= { dot11WNMEventWNMLogReportEntry 1 }
dot11WNMEventWNMLogRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMEventWNMLogReportEntry 2 }
dot11WNMEventWNMLogRprtIfIndex OBJECT-TYPE
SYNTAX InterfaceIndex
MAX-ACCESS read-only
STATUS current
DESCRIPTION
"The ifIndex for this row of WNMEventWNMLog Report has been received on."
::= { dot11WNMEventWNMLogReportEntry 3 }
dot11WNMEventWNMLogRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMEventWNMLogReportEntry 4 }
dot11WNMEventWNMLogRprtEventTSF OBJECT-TYPE
SYNTAX TSFType
MAX-ACCESS read-only
STATUS current
DESCRIPTION
"This is a status variable.
It is written by the SME when a management report is completed.
This attribute contains the value of the Event timestamp field."
::= { dot11WNMEventWNMLogReportEntry 5 }
dot11WNMEventWNMLogRprtUTCOffset OBJECT-TYPE
SYNTAX OCTET STRING (SIZE(10))
MAX-ACCESS read-only
STATUS current
DESCRIPTION
"This is a status variable.
It is written by the SME when a management report is completed.
This attribute indicates the UTC Offset Time Value optionally included in
the Event Report."
::= { dot11WNMEventWNMLogReportEntry 6 }
dot11WNMEventWNMLogRprtTimeError OBJECT-TYPE
SYNTAX OCTET STRING (SIZE(5))
MAX-ACCESS read-only
STATUS current
DESCRIPTION
"This is a status variable.
It is written by the SME when a management report is completed.
This attribute contains the value of the Event Time Error field optionally
included in the Event Report."
::= { dot11WNMEventWNMLogReportEntry 7 }
dot11WNMEventWNMLogRprtContent OBJECT-TYPE
SYNTAX OCTET STRING (SIZE(0..2284))
MAX-ACCESS read-only
STATUS current
DESCRIPTION
"This is a status variable.
It is written by the SME when a management report is completed.
This attribute contains the entire syslog message, consisting of the PRI,
HEADER, and MSG portion of a WNM Log message as described in IETF RFC
3164-2001. The TAG field of the MSG portion of the message is a 17 octet
string containing the ASCII representation of the STA MAC address using
hexadecimal notation with colons between octets. The octet containing the
individual/group bit occurs last, and that bit is in the least significant
position within that octet. See 10.23.2.5."
::= { dot11WNMEventWNMLogReportEntry 8 }
-- ********************************************************************
-- * End of dot11WNMEventWNMLogReport TABLE
-- ********************************************************************
-- ********************************************************************
-- * dot11WNMDiagMfrInfoReport TABLE
-- ********************************************************************
dot11WNMDiagMfrInfoReportTable OBJECT-TYPE
SYNTAX SEQUENCE OF Dot11WNMDiagMfrInfoReportEntry
MAX-ACCESS not-accessible
STATUS current
DESCRIPTION
"Group contains the current list of Manufacturer Information STA reports
that have been received by the MLME. The report tables shall be maintained
as FIFO to preserve freshness, thus the rows in this table can be deleted
for memory constraints or other implementation constraints determined by
the vendor. New rows shall have different RprtIndex values than those
deleted within the range limitation of the index. One easy way is to monotonically
increase RprtIndex for new reports being written in the table."
::= { dot11WNMReport 9 }
dot11WNMDiagMfrInfoReportEntry OBJECT-TYPE
SYNTAX Dot11WNMDiagMfrInfoReportEntry
MAX-ACCESS not-accessible
STATUS current
DESCRIPTION
"An entry in the dot11WNMDiagMfrInfoReportTable Indexed by
dot11WNMDiagMfrInfoRprtIndex."
INDEX { dot11WNMDiagMfrInfoRprtIndex }
::= { dot11WNMDiagMfrInfoReportTable 1 }
Dot11WNMDiagMfrInfoReportEntry ::=
SEQUENCE {
dot11WNMDiagMfrInfoRprtIndex Unsigned32,
dot11WNMDiagMfrInfoRprtRqstToken OCTET STRING,
dot11WNMDiagMfrInfoRprtIfIndex InterfaceIndex,
dot11WNMDiagMfrInfoRprtEventStatus INTEGER,
dot11WNMDiagMfrInfoRprtMfrOi OCTET STRING,
dot11WNMDiagMfrInfoRprtMfrIdString OCTET STRING,
dot11WNMDiagMfrInfoRprtMfrModelString OCTET STRING,
dot11WNMDiagMfrInfoRprtMfrSerialNumberString OCTET STRING,
dot11WNMDiagMfrInfoRprtMfrFirmwareVersion OCTET STRING,
dot11WNMDiagMfrInfoRprtMfrAntennaType OCTET STRING,
dot11WNMDiagMfrInfoRprtCollocRadioType INTEGER,
dot11WNMDiagMfrInfoRprtDeviceType INTEGER,
dot11WNMDiagMfrInfoRprtCertificateID OCTET STRING}
dot11WNMDiagMfrInfoRprtIndex OBJECT-TYPE
SYNTAX Unsigned32
MAX-ACCESS not-accessible
STATUS current
DESCRIPTION
"Index for Manufacturer Information STA Report elements in
dot11WNMDiagMfrInfoReportTable, greater than 0."
::= { dot11WNMDiagMfrInfoReportEntry 1 }
dot11WNMDiagMfrInfoRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMDiagMfrInfoReportEntry 2 }
dot11WNMDiagMfrInfoRprtIfIndex OBJECT-TYPE
SYNTAX InterfaceIndex
MAX-ACCESS read-only
STATUS current
DESCRIPTION
"The ifIndex for this row of WNMDiagMfrInfo Report has been received on."
::= { dot11WNMDiagMfrInfoReportEntry 3 }
dot11WNMDiagMfrInfoRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMDiagMfrInfoReportEntry 4}
dot11WNMDiagMfrInfoRprtMfrOi OBJECT-TYPE
SYNTAX OCTET STRING (SIZE(0..5))
MAX-ACCESS read-only
STATUS current
DESCRIPTION
"This is a status variable.
It is written by the SME when a management report is completed.
This attribute indicates the Manufacturer OI for the reported Manufacturer
Information STA Diagnostic. The OUI attribute contains an organizationally
unique identifier, the first 24-bits of the network connected device that
indicate the specific vendor for that device."
::= { dot11WNMDiagMfrInfoReportEntry 5 }
dot11WNMDiagMfrInfoRprtMfrIdString OBJECT-TYPE
SYNTAX OCTET STRING (SIZE(0..255))
MAX-ACCESS read-only
STATUS current
DESCRIPTION
"This is a status variable.
It is written by the SME when a management report is completed.
This attribute indicates the Manufacturer ID string for the reported Manufacturer
Information STA Diagnostic. The ID attribute contains an ASCII
string indicating the manufacturer identifier of the wireless network
adaptor. This string is not null terminated."
::= { dot11WNMDiagMfrInfoReportEntry 6 }
dot11WNMDiagMfrInfoRprtMfrModelString OBJECT-TYPE
SYNTAX OCTET STRING (SIZE(0..255))
MAX-ACCESS read-only
STATUS current
DESCRIPTION
"This is a status variable.
It is written by the SME when a management report is completed.
This attribute indicates the Manufacturer model string for the reported
Manufacturer Information STA Diagnostic. The model attribute contains an
ASCII string indicating the model of the wireless network adaptor. This
string is not null terminated."
::= { dot11WNMDiagMfrInfoReportEntry 7 }
dot11WNMDiagMfrInfoRprtMfrSerialNumberString OBJECT-TYPE
SYNTAX OCTET STRING (SIZE(0..255))
MAX-ACCESS read-only
STATUS current
DESCRIPTION
"This is a status variable.
It is written by the SME when a management report is completed.
This attribute indicates the Manufacturer serial number string for the
reported Manufacturer Information STA Diagnostic. The serial number attribute
contains an ASCII string indicating the serial number of the wireless
network adaptor. This string is not null terminated."
::= { dot11WNMDiagMfrInfoReportEntry 8 }
dot11WNMDiagMfrInfoRprtMfrFirmwareVersion OBJECT-TYPE
SYNTAX OCTET STRING (SIZE(0..255))
MAX-ACCESS read-only
STATUS current
DESCRIPTION
"This is a status variable.
It is written by the SME when a management report is completed.
This attribute indicates the Manufacturer firmware version string for the
reported Manufacturer Information STA Diagnostic. The firmware version
attribute contains an ASCII string identifying the version of firmware
currently installed on the wireless network adaptor. This string is not
null terminated."
::= { dot11WNMDiagMfrInfoReportEntry 9 }
dot11WNMDiagMfrInfoRprtMfrAntennaType OBJECT-TYPE
SYNTAX OCTET STRING (SIZE(0..255))
MAX-ACCESS read-only
STATUS current
DESCRIPTION
"This is a status variable.
It is written by the SME when a management report is completed.
This attribute indicates the Manufacturer antenna type string for the
reported Manufacturer Information STA Diagnostic. The first octet of this
string indicates the antenna count, and the second octet indicates the
antenna gain. The antenna gain indicates the peak gain in dBi of the
antenna connected to the wireless network adaptor. The remaining octets
contain an ASCII string indicating the type of antenna connected to the
wireless network adaptor."
::= { dot11WNMDiagMfrInfoReportEntry 10 }
dot11WNMDiagMfrInfoRprtCollocRadioType OBJECT-TYPE
SYNTAX INTEGER {
reserved(0),
cellular(1),
cordless(2),
gps(3),
ieee80211(4),
ieee80215(5),
ieee80216(6),
ieee80220(7),
ieee80222(8),
digitalAudioBroadcasting(9),
digitalVideoBroadcasting(10)
}
MAX-ACCESS read-only
STATUS current
DESCRIPTION
"This is a status variable.
It is written by the SME when a management report is completed.
This attribute contains the type of the collocated radio."
::= { dot11WNMDiagMfrInfoReportEntry 11 }
dot11WNMDiagMfrInfoRprtDeviceType OBJECT-TYPE
SYNTAX INTEGER {
reserved(0),
referenceDesign(1),
accessPointWirelessRouterSoho(2),
enterpriseAccessPoint(3),
broadbandGateway(4),
digitalStillCamera(5),
portableVideoCamera(6),
networkedWebCamera(7),
digitalAudioStationary(8),
digitalAudioPortable(9),
setTopBoxMediaServer(10),
tvMonitorDigitalPictureFrame(11),
gameConsoleGameAdaptor(12),
gamingDevice(13),
mediaServerMediaAdaptor(14),
networkStorageDevice(15),
externalCard(16),
internalCard(17),
ultraMobilPc(18),
notebookComputer(19),
personalDigitalAssistant(20),
printerPrintServer(21),
phoneDualMode(22),
phoneSingleMode(23),
smartphoneDualMode(24),
smartphoneSingleMode(25),
otherDevices(221)
}
MAX-ACCESS read-only
STATUS current
DESCRIPTION
"This is a status variable.
It is written by the SME when a management report is completed.
This attribute indicates the type of device in which the IEEE 802.11 STA
resides."
::= { dot11WNMDiagMfrInfoReportEntry 12 }
dot11WNMDiagMfrInfoRprtCertificateID OBJECT-TYPE
SYNTAX OCTET STRING (SIZE(0..251))
MAX-ACCESS read-only
STATUS current
DESCRIPTION
"This is a status variable.
It is written by the SME when a management report is completed.
This attribute indicates the Certificate ID for the
reported Manufacturer Information STA Diagnostic."
::= { dot11WNMDiagMfrInfoReportEntry 13 }
-- ********************************************************************
-- * End of dot11WNMDiagMfrInfoReport TABLE
-- ********************************************************************
-- ********************************************************************
-- * dot11WNMDiagConfigProfReport TABLE
-- ********************************************************************
dot11WNMDiagConfigProfReportTable OBJECT-TYPE
SYNTAX SEQUENCE OF Dot11WNMDiagConfigProfReportEntry
MAX-ACCESS not-accessible
STATUS current
DESCRIPTION
"Group contains the current list of Configuration Profile reports that
have been received by the MLME. The report tables shall be maintained as
FIFO to preserve freshness, thus the rows in this table can be deleted for
memory constraints or other implementation constraints determined by the
vendor. New rows shall have different RprtIndex values than those deleted
within the range limitation of the index. One easy way is to monotonically
increase RprtIndex for new reports being written in the table."
::= { dot11WNMReport 10 }
dot11WNMDiagConfigProfReportEntry OBJECT-TYPE
SYNTAX Dot11WNMDiagConfigProfReportEntry
MAX-ACCESS not-accessible
STATUS current
DESCRIPTION
"An entry in the dot11WNMDiagConfigProfReportTable Indexed by
dot11WNMDiagConfigProfRprtIndex."
INDEX { dot11WNMDiagConfigProfRprtIndex }
::= { dot11WNMDiagConfigProfReportTable 1 }
Dot11WNMDiagConfigProfReportEntry ::=
SEQUENCE {
dot11WNMDiagConfigProfRprtIndex Unsigned32,
dot11WNMDiagConfigProfRprtRqstToken OCTET STRING,
dot11WNMDiagConfigProfRprtIfIndex InterfaceIndex,
dot11WNMDiagConfigProfRprtEventStatus INTEGER,
dot11WNMDiagConfigProfRprtProfileId Unsigned32,
dot11WNMDiagConfigProfRprtSupportedOperatingClasses OCTET STRING,
dot11WNMDiagConfigProfRprtTxPowerMode INTEGER,
dot11WNMDiagConfigProfRprtTxPowerLevels OCTET STRING,
dot11WNMDiagConfigProfRprtCipherSuite OCTET STRING,
dot11WNMDiagConfigProfRprtAkmSuite OCTET STRING,
dot11WNMDiagConfigProfRprtEapType Unsigned32,
dot11WNMDiagConfigProfRprtEapVendorID OCTET STRING,
dot11WNMDiagConfigProfRprtEapVendorType OCTET STRING,
dot11WNMDiagConfigProfRprtCredentialType INTEGER,
dot11WNMDiagConfigProfRprtSSID OCTET STRING,
dot11WNMDiagConfigProfRprtPowerSaveMode INTEGER }
dot11WNMDiagConfigProfRprtIndex OBJECT-TYPE
SYNTAX Unsigned32
MAX-ACCESS not-accessible
STATUS current
DESCRIPTION
"Index for Configuration Profile Report elements in
dot11WNMDiagConfigProfReportTable, greater than 0."
::= { dot11WNMDiagConfigProfReportEntry 1 }
dot11WNMDiagConfigProfRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMDiagConfigProfReportEntry 2 }
dot11WNMDiagConfigProfRprtIfIndex OBJECT-TYPE
SYNTAX InterfaceIndex
MAX-ACCESS read-only
STATUS current
DESCRIPTION
"The ifIndex for this row of WNMDiagConfigProf Report has been received
on."
::= { dot11WNMDiagConfigProfReportEntry 3 }
dot11WNMDiagConfigProfRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMDiagConfigProfReportEntry 4}
dot11WNMDiagConfigProfRprtProfileId OBJECT-TYPE
SYNTAX Unsigned32 (0..255)
MAX-ACCESS read-only
STATUS current
DESCRIPTION
"This is a status variable.
It is written by the SME when a management report is completed.
This attribute indicates a unique identifier for referencing a configuration
profile available on a device. The value of the identifier can be any
arbitrary value, as long as it is uniquely associated to a single configuration
profile on the device sending the identifier."
::= { dot11WNMDiagConfigProfReportEntry 5 }
dot11WNMDiagConfigProfRprtSupportedOperatingClasses OBJECT-TYPE
SYNTAX OCTET STRING (SIZE(0..255))
MAX-ACCESS read-only
STATUS current
DESCRIPTION
"This is a status variable.
It is written by the SME when a management report is completed.
This attribute indicates the current Operating Class followed by a list of
each Supported Operating Class, as defined in 8.4.2.56. Each octet contains
an integer representing a operating class. Operating Classes are
defined in Annex E. The default value is null."
DEFVAL { ''H }
::= { dot11WNMDiagConfigProfReportEntry 6 }
dot11WNMDiagConfigProfRprtTxPowerMode OBJECT-TYPE
SYNTAX INTEGER {
fixedPowerMode(0),
automaticPowerMode(1)
}
MAX-ACCESS read-only
STATUS current
DESCRIPTION
"This is a status variable.
It is written by the SME when a management report is completed.
This attribute indicates the power mode of the STA."
::= { dot11WNMDiagConfigProfReportEntry 7 }
dot11WNMDiagConfigProfRprtTxPowerLevels OBJECT-TYPE
SYNTAX OCTET STRING (SIZE(1..255))
MAX-ACCESS read-only
STATUS current
DESCRIPTION
"This is a status variable.
It is written by the SME when a management report is completed.
This attribute lists the power levels for the STA. Each octet contains an
integer representing a power level encoded as a 2's complement value in
dBm, rounded to the nearest integer. If the Power Mode is automatic, the
list contains only the minimum and the maximum power levels for the STA.
If the Power Mode is fixed, the list contains one or more fixed power
level settings available at this STA, arranged in increasing numerical
order."
::= { dot11WNMDiagConfigProfReportEntry 8 }
dot11WNMDiagConfigProfRprtCipherSuite OBJECT-TYPE
SYNTAX OCTET STRING (SIZE(4))
MAX-ACCESS read-only
STATUS current
DESCRIPTION
"This is a status variable.
It is written by the SME when a management report is completed.
This attribute indicates the cipher suite, as defined in Table 8-99. The
first three octets indicate the OUI. The last octet indicates the suite
type."
::= { dot11WNMDiagConfigProfReportEntry 9 }
dot11WNMDiagConfigProfRprtAkmSuite OBJECT-TYPE
SYNTAX OCTET STRING (SIZE(4))
MAX-ACCESS read-only
STATUS current
DESCRIPTION
"This is a status variable.
It is written by the SME when a management report is completed.
This attribute indicates the AKM suite, as defined in Table 8-101 in
8.4.2.27.3. The first three octets indicate the OUI. The last octet indicates
the suite type."
::= { dot11WNMDiagConfigProfReportEntry 10 }
dot11WNMDiagConfigProfRprtEapType OBJECT-TYPE
SYNTAX Unsigned32 (0..255)
MAX-ACCESS read-only
STATUS current
DESCRIPTION
"This is a status variable.
It is written by the SME when a management report is completed.
This attribute indicates the single EAP method used by the STA. Valid EAP
Type numbers are assigned by IANA and are defined at http://www.iana.org/
assignments/eap-numbers."
::= { dot11WNMDiagConfigProfReportEntry 11 }
dot11WNMDiagConfigProfRprtEapVendorID OBJECT-TYPE
SYNTAX OCTET STRING (SIZE(0..3))
MAX-ACCESS read-only
STATUS current
DESCRIPTION
"This is a status variable.
It is written by the SME when a management report is completed.
This attribute indicates the EAP Vendor ID number for the EAP method used
by the STA. The EAP Vendor ID field is included when the EAP Type field is
set to 254, and is excluded otherwise."
::= { dot11WNMDiagConfigProfReportEntry 12 }
dot11WNMDiagConfigProfRprtEapVendorType OBJECT-TYPE
SYNTAX OCTET STRING (SIZE(0..4))
MAX-ACCESS read-only
STATUS current
DESCRIPTION
"This is a status variable.
It is written by the SME when a management report is completed.
This attribute indicates the EAP Vendor Type number for the EAP method
used by the STA. The EAP Vendor Type field is included when the EAP Type
field is set to 254, and is excluded otherwise."
::= { dot11WNMDiagConfigProfReportEntry 13 }
dot11WNMDiagConfigProfRprtCredentialType OBJECT-TYPE
SYNTAX INTEGER {
none(0),
preSharedKey(1),
userNamePassword(2),
x509Certificate(3),
otherCertificate(4),
oneTimePassword(5),
token(6)
}
MAX-ACCESS read-only
STATUS current
DESCRIPTION
"This is a status variable.
It is written by the SME when a management report is completed.
This attribute indicates the type of IEEE 802.1X credentials used by the
STA for this authentication diagnostic."
::= { dot11WNMDiagConfigProfReportEntry 14 }
dot11WNMDiagConfigProfRprtSSID OBJECT-TYPE
SYNTAX OCTET STRING (SIZE(1..32))
MAX-ACCESS read-only
STATUS current
DESCRIPTION
"This is a status variable.
It is written by the SME when a management report is completed.
This attribute indicates the SSID for the diagnostic report, as defined in
8.4.2.2."
::= { dot11WNMDiagConfigProfReportEntry 15 }
dot11WNMDiagConfigProfRprtPowerSaveMode OBJECT-TYPE
SYNTAX INTEGER {
unknownMode(0),
none(1),
psDtims1Mode(2),
psDtims0Mode(3),
uapsdMode(4),
sapsdMode(5),
upsmpMode(6),
spsmpMode(7),
smpsMode(8),
wnmSleepMode(9),
fmsMode(10),
timBroadcastMode(11),
tfsMode(12),
tdlsPeerUapsdMode(13),
tdlsPeerPsmMode(14)
}
MAX-ACCESS read-only
STATUS current
DESCRIPTION
"This is a status variable.
It is written by the SME when a management report is completed.
This attribute indicates the power save mode in use by the STA, as defined
in Table 8-147."
::= { dot11WNMDiagConfigProfReportEntry 16 }
-- ********************************************************************
-- * End of dot11WNMDiagConfigProfReport TABLE
-- ********************************************************************
-- ********************************************************************
-- * dot11WNMDiagAssocReport TABLE
-- ********************************************************************
dot11WNMDiagAssocReportTable OBJECT-TYPE
SYNTAX SEQUENCE OF Dot11WNMDiagAssocReportEntry
MAX-ACCESS not-accessible
STATUS current
DESCRIPTION
"Group contains the current list of Association Diagnostic reports that
have been received by the MLME. The report tables shall be maintained as
FIFO to preserve freshness, thus the rows in this table can be deleted for
memory constraints or other implementation constraints determined by the
vendor. New rows shall have different RprtIndex values than those deleted
within the range limitation of the index. One easy way is to monotonically
increase RprtIndex for new reports being written in the table."
::= { dot11WNMReport 11 }
dot11WNMDiagAssocReportEntry OBJECT-TYPE
SYNTAX Dot11WNMDiagAssocReportEntry
MAX-ACCESS not-accessible
STATUS current
DESCRIPTION
"An entry in the dot11WNMDiagAssocReportTable Indexed by
dot11WNMDiagAssocRprtIndex."
INDEX { dot11WNMDiagAssocRprtIndex }
::= { dot11WNMDiagAssocReportTable 1 }
Dot11WNMDiagAssocReportEntry ::=
SEQUENCE {
dot11WNMDiagAssocRprtIndex Unsigned32,
dot11WNMDiagAssocRprtRqstToken OCTET STRING,
dot11WNMDiagAssocRprtIfIndex InterfaceIndex,
dot11WNMDiagAssocRprtEventStatus INTEGER,
dot11WNMDiagAssocRprtBssid MacAddress,
dot11WNMDiagAssocRprtOperatingClass Unsigned32,
dot11WNMDiagAssocRprtChannelNumber Unsigned32,
dot11WNMDiagAssocRprtStatusCode Unsigned32 }
dot11WNMDiagAssocRprtIndex OBJECT-TYPE
SYNTAX Unsigned32
MAX-ACCESS not-accessible
STATUS current
DESCRIPTION
"Index for Association Diagnostic Report elements in
dot11WNMDiagAssocReportTable, greater than 0."
::= { dot11WNMDiagAssocReportEntry 1 }
dot11WNMDiagAssocRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMDiagAssocReportEntry 2 }
dot11WNMDiagAssocRprtIfIndex OBJECT-TYPE
SYNTAX InterfaceIndex
MAX-ACCESS read-only
STATUS current
DESCRIPTION
"The ifIndex for this row of WNMDiagAssoc Report has been received on."
::= { dot11WNMDiagAssocReportEntry 3 }
dot11WNMDiagAssocRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMDiagAssocReportEntry 4 }
dot11WNMDiagAssocRprtBssid OBJECT-TYPE
SYNTAX MacAddress
MAX-ACCESS read-only
STATUS current
DESCRIPTION
"This is a status variable.
It is written by the SME when a management report is completed.
This attribute indicates the BSSID for the target AP for this Association
Diagnostic Report."
::= { dot11WNMDiagAssocReportEntry 5 }
dot11WNMDiagAssocRprtOperatingClass OBJECT-TYPE
SYNTAX Unsigned32(1..255)
MAX-ACCESS read-only
STATUS current
DESCRIPTION
"This is a status variable.
It is written by the SME when a management report is completed.
This attribute indicates the channel set for the target AP for this Association
Diagnostic Report. Country, Operating Class and Channel Number
together specify the channel frequency and spacing for this measurement
request. Valid values of Operating Class as shown in Annex E."
::= { dot11WNMDiagAssocReportEntry 6 }
dot11WNMDiagAssocRprtChannelNumber OBJECT-TYPE
SYNTAX Unsigned32 (1..255)
MAX-ACCESS read-only
STATUS current
DESCRIPTION
"This is a status variable.
It is written by the SME when a management report is completed.
This attribute indicates the operating channel of the target AP for this
Association Diagnostic Report. The Channel Number is only defined within
the indicated Operating Class as sown in Annex E."
::= { dot11WNMDiagAssocReportEntry 7 }
dot11WNMDiagAssocRprtStatusCode OBJECT-TYPE
SYNTAX Unsigned32(0..65535)
MAX-ACCESS read-only
STATUS current
DESCRIPTION
"This is a status variable.
It is written by the SME when a management report is completed.
This attribute indicates the result of the association diagnostic and is
set to one of the status codes specified in Table 8-37 in 8.4.1.9."
::= { dot11WNMDiagAssocReportEntry 8 }
-- ********************************************************************
-- * End of dot11WNMDiagAssocReport TABLE
-- ********************************************************************
-- ********************************************************************
-- * dot11WNMDiag8021xAuthReport TABLE
-- ********************************************************************
dot11WNMDiag8021xAuthReportTable OBJECT-TYPE
SYNTAX SEQUENCE OF Dot11WNMDiag8021xAuthReportEntry
MAX-ACCESS not-accessible
STATUS current
DESCRIPTION
"Group contains the current list of IEEE 802.1X Authentication Diagnostic
reports that have been received by the MLME. The report tables shall be
maintained as FIFO to preserve freshness, thus the rows in this table can
be deleted for memory constraints or other implementation constraints
determined by the vendor. New rows shall have different RprtIndex values
than those deleted within the range limitation of the index. One easy way
is to monotonically increase RprtIndex for new reports being written in
the table."
::= { dot11WNMReport 12 }
dot11WNMDiag8021xAuthReportEntry OBJECT-TYPE
SYNTAX Dot11WNMDiag8021xAuthReportEntry
MAX-ACCESS not-accessible
STATUS current
DESCRIPTION
"An entry in the dot11WNMDiag8021xAuthReportTable Indexed by
dot11WNMDiag8021xAuthRprtIndex."
INDEX { dot11WNMDiag8021xAuthRprtIndex }
::= { dot11WNMDiag8021xAuthReportTable 1 }
Dot11WNMDiag8021xAuthReportEntry ::=
SEQUENCE {
dot11WNMDiag8021xAuthRprtIndex Unsigned32,
dot11WNMDiag8021xAuthRprtRqstToken OCTET STRING,
dot11WNMDiag8021xAuthRprtIfIndex InterfaceIndex,
dot11WNMDiag8021xAuthRprtEventStatus INTEGER,
dot11WNMDiag8021xAuthRprtBssid MacAddress,
dot11WNMDiag8021xAuthRprtOperatingClass Unsigned32,
dot11WNMDiag8021xAuthRprtChannelNumber Unsigned32,
dot11WNMDiag8021xAuthRprtEapType Unsigned32,
dot11WNMDiag8021xAuthRprtEapVendorID OCTET STRING,
dot11WNMDiag8021xAuthRprtEapVendorType OCTET STRING,
dot11WNMDiag8021xAuthRprtCredentialType INTEGER,
dot11WNMDiag8021xAuthRprtStatusCode Unsigned32 }
dot11WNMDiag8021xAuthRprtIndex OBJECT-TYPE
SYNTAX Unsigned32
MAX-ACCESS not-accessible
STATUS current
DESCRIPTION
"Index for IEEE 802.1X Authentication Diagnostic Report elements in
dot11WNMDiag8021xAuthReportTable, greater than 0."
::= { dot11WNMDiag8021xAuthReportEntry 1 }
dot11WNMDiag8021xAuthRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMDiag8021xAuthReportEntry 2 }
dot11WNMDiag8021xAuthRprtIfIndex OBJECT-TYPE
SYNTAX InterfaceIndex
MAX-ACCESS read-only
STATUS current
DESCRIPTION
"The ifIndex for this row of WNMDiag8021xAuth Report has been received
on."
::= { dot11WNMDiag8021xAuthReportEntry 3 }
dot11WNMDiag8021xAuthRprtEventStatus OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the status value included in the Event Report."
::= { dot11WNMDiag8021xAuthReportEntry 4 }
dot11WNMDiag8021xAuthRprtBssid OBJECT-TYPE
SYNTAX MacAddress
MAX-ACCESS read-only
STATUS current
DESCRIPTION
"This is a status variable.
It is written by the SME when a management report is completed.
This attribute indicates the BSSID for the target AP for this Authentication
Diagnostic Report."
::= { dot11WNMDiag8021xAuthReportEntry 5 }
dot11WNMDiag8021xAuthRprtOperatingClass OBJECT-TYPE
SYNTAX Unsigned32(1..255)
MAX-ACCESS read-only
STATUS current
DESCRIPTION
"This is a status variable.
It is written by the SME when a management report is completed.
This attribute indicates the channel set for the target AP for this
Authentication Diagnostic Report. Country, Operating Class and Channel
Number together specify the channel frequency and spacing for this measurement
request. Valid values of Operating Class as shown in Annex E."
::= { dot11WNMDiag8021xAuthReportEntry 6 }
dot11WNMDiag8021xAuthRprtChannelNumber OBJECT-TYPE
SYNTAX Unsigned32 (1..255)
MAX-ACCESS read-only
STATUS current
DESCRIPTION
"This is a status variable.
It is written by the SME when a management report is completed.
This attribute indicates the operating channel of the target AP for this
Authentication Diagnostic Report. The Channel Number is only defined
within the indicated Operating Class as shown in Annex E."
::= { dot11WNMDiag8021xAuthReportEntry 7 }
dot11WNMDiag8021xAuthRprtEapType OBJECT-TYPE
SYNTAX Unsigned32 (0..255)
MAX-ACCESS read-only
STATUS current
DESCRIPTION
"This is a status variable.
It is written by the SME when a management report is completed.
This attribute indicates the single EAP method used by the STA. Valid EAP
Type numbers are assigned by IANA and are defined at http://www.iana.org/
assignments/eap-numbers."
::= { dot11WNMDiag8021xAuthReportEntry 8 }
dot11WNMDiag8021xAuthRprtEapVendorID OBJECT-TYPE
SYNTAX OCTET STRING (SIZE(0..3))
MAX-ACCESS read-only
STATUS current
DESCRIPTION
"This is a status variable.
It is written by the SME when a management report is completed.
This attribute indicates the EAP Vendor ID number for the EAP method used
by the STA. The EAP Vendor ID field is included when the EAP Type field is
set to 254, and is excluded otherwise."
::= { dot11WNMDiag8021xAuthReportEntry 9 }
dot11WNMDiag8021xAuthRprtEapVendorType OBJECT-TYPE
SYNTAX OCTET STRING (SIZE(0..4))
MAX-ACCESS read-only
STATUS current
DESCRIPTION
"This is a status variable.
It is written by the SME when a management report is completed.
This attribute indicates the EAP Vendor Type number for the EAP method
used by the STA. The EAP Vendor Type field is included when the EAP Type
field is set to 254, and is excluded otherwise."
::= { dot11WNMDiag8021xAuthReportEntry 10 }
dot11WNMDiag8021xAuthRprtCredentialType OBJECT-TYPE
SYNTAX INTEGER {
none(0),
preSharedKey(1),
userNamePassword(2),
x509Certificate(3),
otherCertificate(4),
oneTimePassword(5),
token(6)
}
MAX-ACCESS read-only
STATUS current
DESCRIPTION
"This is a status variable.
It is written by the SME when a management report is completed.
This attribute indicates the type of IEEE 802.1X credentials used by the
STA for this authentication diagnostic."
::= { dot11WNMDiag8021xAuthReportEntry 11 }
dot11WNMDiag8021xAuthRprtStatusCode OBJECT-TYPE
SYNTAX Unsigned32 (0..65535)
MAX-ACCESS read-only
STATUS current
DESCRIPTION
"This is a status variable.
It is written by the SME when a management report is completed.
This attribute indicates the result of the authentication diagnostic and
is set to one of the status codes specified in Table 8-37."
::= { dot11WNMDiag8021xAuthReportEntry 12 }
-- ********************************************************************
-- * End of dot11WNMDiag8021xAuthReport TABLE
-- ********************************************************************
-- ********************************************************************
-- * dot11WNMLocConfigReport TABLE
-- ********************************************************************
dot11WNMLocConfigReportTable OBJECT-TYPE
SYNTAX SEQUENCE OF Dot11WNMLocConfigReportEntry
MAX-ACCESS not-accessible
STATUS current
DESCRIPTION
"Group contains the current list of Location Configuration reports that
have been received by the MLME. The report tables shall be maintained as
FIFO to preserve freshness, thus the rows in this table can be deleted for
memory constraints or other implementation constraints determined by the
vendor. New rows shall have different RprtIndex values than those deleted
within the range limitation of the index. One easy way is to monotonically
increase RprtIndex for new reports being written in the table."
::= { dot11WNMReport 13 }
dot11WNMLocConfigReportEntry OBJECT-TYPE
SYNTAX Dot11WNMLocConfigReportEntry
MAX-ACCESS not-accessible
STATUS current
DESCRIPTION
"An entry in the dot11WNMLocConfigReportTable Indexed by
dot11WNMLocConfigRprtIndex."
INDEX { dot11WNMLocConfigRprtIndex }
::= { dot11WNMLocConfigReportTable 1 }
Dot11WNMLocConfigReportEntry ::=
SEQUENCE {
dot11WNMLocConfigRprtIndex Unsigned32,
dot11WNMLocConfigRprtRqstToken OCTET STRING,
dot11WNMLocConfigRprtIfIndex InterfaceIndex,
dot11WNMLocConfigRprtLocIndParams OCTET STRING,
dot11WNMLocConfigRprtLocIndChanList OCTET STRING,
dot11WNMLocConfigRprtLocIndBcastRate Unsigned32,
dot11WNMLocConfigRprtLocIndOptions OCTET STRING,
dot11WNMLocConfigRprtStatusConfigSubelemId INTEGER,
dot11WNMLocConfigRprtStatusResult INTEGER,
dot11WNMLocConfigRprtVendorSpecificRprtContent OCTET STRING }
dot11WNMLocConfigRprtIndex OBJECT-TYPE
SYNTAX Unsigned32
MAX-ACCESS not-accessible
STATUS current
DESCRIPTION
"Index for Location Configuration Report elements in
dot11WNMLocConfigReportTable, greater than 0."
::= { dot11WNMLocConfigReportEntry 1 }
dot11WNMLocConfigRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMLocConfigReportEntry 2 }
dot11WNMLocConfigRprtIfIndex OBJECT-TYPE
SYNTAX InterfaceIndex
MAX-ACCESS read-only
STATUS current
DESCRIPTION
"The ifIndex for this row of WNMLocConfig Report has been received on."
::= { dot11WNMLocConfigReportEntry 3 }
dot11WNMLocConfigRprtLocIndParams OBJECT-TYPE
SYNTAX OCTET STRING (SIZE(16))
MAX-ACCESS read-only
STATUS current
DESCRIPTION
"This is a status variable.
It is written by the SME when a management report is completed.
This attribute indicates STA Location reporting characteristics. The format
of these Location Indication Parameters are detailed in 8.4.2.73.2."
::= { dot11WNMLocConfigReportEntry 4 }
dot11WNMLocConfigRprtLocIndChanList OBJECT-TYPE
SYNTAX OCTET STRING (SIZE(0..254))
MAX-ACCESS read-only
STATUS current
DESCRIPTION
"This is a status variable.
It is written by the SME when a management report is completed.
This attribute lists location indication reporting channel information for
this Location Configuration Report. The default value is null. Each pair
of octets indicates a different Operating Class and channel number for
this request. The detailed format for this list of channels as described
in 8.4.2.73.3."
DEFVAL { ''H }
::= { dot11WNMLocConfigReportEntry 5 }
dot11WNMLocConfigRprtLocIndBcastRate OBJECT-TYPE
SYNTAX Unsigned32 (0..65535)
UNITS "0.5Mb/s"
MAX-ACCESS read-only
STATUS current
DESCRIPTION
"This is a status variable.
It is written by the SME when a management report is completed.
This attribute indicates the data rate, in 0.5Mb/s units, at which the STA
broadcasts its Location Track Notification frames."
::= { dot11WNMLocConfigReportEntry 6 }
dot11WNMLocConfigRprtLocIndOptions OBJECT-TYPE
SYNTAX OCTET STRING (SIZE(0..255))
MAX-ACCESS read-only
STATUS current
DESCRIPTION
"This is a status variable.
It is written by the SME when a management report is completed.
This attribute indicates the location track indication options used; see
8.4.2.73.9."
::= { dot11WNMLocConfigReportEntry 7}
dot11WNMLocConfigRprtStatusConfigSubelemId OBJECT-TYPE
SYNTAX INTEGER {
multipleSubelemIds(0),
locationIndicationParams(1),
locationIndicationChannels(2),
locationStatus(3),
radioInformation(4),
motion(5),
locationIndicationBcastDataRate(6),
timeOfDeparture(7),
vendorSpecific(8)
}
MAX-ACCESS read-only
STATUS current
DESCRIPTION
"This is a status variable.
It is written by the SME when a management report is completed.
This attribute is set to a specific Location Parameters subelement ID
transmitted in a Location Configuration Request frame. If the following
StatusResult attribute field value applies to more than one subelement
then the Config subelement ID is set to 0. If the Status field value
applies to one subelement, then a Location Status subelement may be
included in the Location Configuration Response for each configuration
subelement that has a non-Success Status value."
::= { dot11WNMLocConfigReportEntry 8 }
dot11WNMLocConfigRprtStatusResult OBJECT-TYPE
SYNTAX INTEGER {
successful(0),
requestFailed(1),
requestRefused(2),
requestIncapable(3),
detectedFrequentTransition(4)
}
MAX-ACCESS read-only
STATUS current
DESCRIPTION
"This is a status variable.
It is written by the SME when a management report is completed.
This attribute contains the resulting status of the Location Configuration
Request frame for the indicated Location Parameter subelement ID, as
listed in Table 8-137, Event Report Status."
::= { dot11WNMLocConfigReportEntry 9 }
dot11WNMLocConfigRprtVendorSpecificRprtContent OBJECT-TYPE
SYNTAX OCTET STRING (SIZE(0..255))
MAX-ACCESS read-only
STATUS current
DESCRIPTION
"This is a status variable.
It is written by the SME when a management report is completed.
This attribute provides an envelope for all the vendor specific subelements
that may be included in Location Configuration Report element. The
default value is null."
DEFVAL { ''H }
::= { dot11WNMLocConfigReportEntry 10 }
-- ********************************************************************
-- * End of dot11WNMLocConfigReport TABLE
-- ********************************************************************
-- ********************************************************************
-- * dot11WNMBssTransitReport TABLE
-- ********************************************************************
dot11WNMBssTransitReportTable OBJECT-TYPE
SYNTAX SEQUENCE OF Dot11WNMBssTransitReportEntry
MAX-ACCESS not-accessible
STATUS current
DESCRIPTION
"Group contains the current list of BSS Transition Management reports that
have been received by the MLME. The report tables shall be maintained as
FIFO to preserve freshness, thus the rows in this table can be deleted for
memory constraints or other implementation constraints determined by the
vendor. New rows shall have different RprtIndex values than those deleted
within the range limitation of the index. One easy way is to monotonically
increase RprtIndex for new reports being written in the table."
::= { dot11WNMReport 14 }
dot11WNMBssTransitReportEntry OBJECT-TYPE
SYNTAX Dot11WNMBssTransitReportEntry
MAX-ACCESS not-accessible
STATUS current
DESCRIPTION
"An entry in the dot11WNMBssTransitReportTable Indexed by
dot11WNMBssTransitRprtIndex."
INDEX { dot11WNMBssTransitRprtIndex }
::= { dot11WNMBssTransitReportTable 1 }
Dot11WNMBssTransitReportEntry ::=
SEQUENCE {
dot11WNMBssTransitRprtIndex Unsigned32,
dot11WNMBssTransitRprtRqstToken OCTET STRING,
dot11WNMBssTransitRprtIfIndex InterfaceIndex,
dot11WNMBssTransitRprtStatusCode INTEGER,
dot11WNMBssTransitRprtBSSTerminationDelay Unsigned32,
dot11WNMBssTransitRprtTargetBssid MacAddress,
dot11WNMBssTransitRprtCandidateList OCTET STRING }
dot11WNMBssTransitRprtIndex OBJECT-TYPE
SYNTAX Unsigned32
MAX-ACCESS not-accessible
STATUS current
DESCRIPTION
"Index for BSS Transition Management Report elements in
dot11WNMBssTransitReportTable, greater than 0."
::= { dot11WNMBssTransitReportEntry 1 }
dot11WNMBssTransitRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMBssTransitReportEntry 2 }
dot11WNMBssTransitRprtIfIndex OBJECT-TYPE
SYNTAX InterfaceIndex
MAX-ACCESS read-only
STATUS current
DESCRIPTION
"The ifIndex for this row of WNMBssTransit Report has been received on."
::= { dot11WNMBssTransitReportEntry 3 }
dot11WNMBssTransitRprtStatusCode OBJECT-TYPE
SYNTAX INTEGER {
accept(0),
rejectUnspecified(1),
rejectInsufficientBeacons(2),
rejectInsufficientCapacity(3),
rejectBssTerminationUndesired(4),
rejectBssTerminationDelayRequest(5),
rejectBssTransitionCandidateListProvided(6),
rejectNoSuitableBssTransitionCandidates(7),
rejectLeavingEss(8)
}
MAX-ACCESS read-only
STATUS current
DESCRIPTION
"This is a status variable.
It is written by the SME when a management report is completed.
This attribute indicates the status of this BSS Transition report."
::= { dot11WNMBssTransitReportEntry 4 }
dot11WNMBssTransitRprtBSSTerminationDelay OBJECT-TYPE
SYNTAX Unsigned32 (1..255)
UNITS "minutes"
MAX-ACCESS read-only
STATUS current
DESCRIPTION
"This is a status variable.
It is written by the SME when a management report is completed.
This attribute indicates the number of minutes that the responding STA
requests the BSS to delay termination. This attribute is included only if
the Status Code field value is set to 5."
::= { dot11WNMBssTransitReportEntry 5 }
dot11WNMBssTransitRprtTargetBssid OBJECT-TYPE
SYNTAX MacAddress
MAX-ACCESS read-only
STATUS current
DESCRIPTION
"This is a status variable.
It is written by the SME when a management report is completed.
This attribute indicates the target BSSID for this BSS Transition Report."
::= { dot11WNMBssTransitReportEntry 6 }
dot11WNMBssTransitRprtCandidateList OBJECT-TYPE
SYNTAX OCTET STRING (SIZE(0..2304))
MAX-ACCESS read-create
STATUS current
DESCRIPTION
"This is a status variable.
It is written by the SME when a management report is completed.
This attribute lists one or more Neighbor Report elements which are BSS
transition candidates for this request. The Neighbore Report elements are
described in 8.4.2.39."
::= { dot11WNMBssTransitReportEntry 7 }
-- ********************************************************************
-- * End of dot11WNMBssTransitReport TABLE
-- ********************************************************************
-- ********************************************************************
-- * dot11WNMColocInterfReport TABLE
-- ********************************************************************
dot11WNMColocInterfReportTable OBJECT-TYPE
SYNTAX SEQUENCE OF Dot11WNMColocInterfReportEntry
MAX-ACCESS not-accessible
STATUS current
DESCRIPTION
"Group contains the current list of Collocated Interference reports that
have been received by the MLME. The report tables shall be maintained as
FIFO to preserve freshness, thus the rows in this table can be deleted for
memory constraints or other implementation constraints determined by the
vendor. New rows shall have different RprtIndex values than those deleted
within the range limitation of the index. One easy way is to monotonically
increase RprtIndex for new reports being written in the table."
::= { dot11WNMReport 16 }
dot11WNMColocInterfReportEntry OBJECT-TYPE
SYNTAX Dot11WNMColocInterfReportEntry
MAX-ACCESS not-accessible
STATUS current
DESCRIPTION
"An entry in the dot11WNMColocInterfReportTable Indexed by
dot11WNMColocInterfRprtIndex."
INDEX { dot11WNMColocInterfRprtIndex }
::= { dot11WNMColocInterfReportTable 1 }
Dot11WNMColocInterfReportEntry ::=
SEQUENCE {
dot11WNMColocInterfRprtIndex Unsigned32,
dot11WNMColocInterfRprtRqstToken OCTET STRING,
dot11WNMColocInterfRprtIfIndex InterfaceIndex,
dot11WNMColocInterfRprtPeriod Unsigned32,
dot11WNMColocInterfRprtInterfLevel Integer32,
dot11WNMColocInterfRprtInterfAccuracy Unsigned32,
dot11WNMColocInterfRprtInterfIndex Unsigned32,
dot11WNMColocInterfRprtInterfInterval Integer32,
dot11WNMColocInterfRprtInterfBurstLength Integer32,
dot11WNMColocInterfRprtInterfStartTime Integer32,
dot11WNMColocInterfRprtInterfCenterFreq Integer32,
dot11WNMColocInterfRprtInterfBandwidth Unsigned32 }
dot11WNMColocInterfRprtIndex OBJECT-TYPE
SYNTAX Unsigned32
MAX-ACCESS not-accessible
STATUS current
DESCRIPTION
"Index for Collocated Interference Report elements in
dot11WNMColocInterfReportTable, greater than 0."
::= { dot11WNMColocInterfReportEntry 1 }
dot11WNMColocInterfRprtRqstToken OBJECT-TYPE
SYNTAX OCTET STRING
MAX-ACCESS read-only
STATUS current
DESCRIPTION
"This is a status variable.
It is written by the SME when a management report is completed.
This attribute indicates the request token that was indicated in the WNM
request that generated this measurement report. This should be an exact
match to the original dot11WNMRqstToken attribute. Note that there may be
multiple entries in the table that match this value since a single request
may generate multiple WNM reports."
::= { dot11WNMColocInterfReportEntry 2 }
dot11WNMColocInterfRprtIfIndex OBJECT-TYPE
SYNTAX InterfaceIndex
MAX-ACCESS read-only
STATUS current
DESCRIPTION
"This is a status variable.
It is written by the SME when a management report is completed.
The ifIndex for this row of WNMColocInterf Report has been received on."
::= { dot11WNMColocInterfReportEntry 3 }
dot11WNMColocInterfRprtPeriod OBJECT-TYPE
SYNTAX Unsigned32(0..255)
UNITS "100 TU"
MAX-ACCESS read-only
STATUS current
DESCRIPTION
"This is a status variable.
It is written by the SME when a management report is completed.
This attribute indicates how often the STA periodically reports the collocated
interference. The field is in units of 100 TUs. If the Report Period
field is set to 0, then the reporting is not periodic, and a report is
generated when the STA detects a change in the collocated interference.
See 10.23.8 for further details."
::= { dot11WNMColocInterfReportEntry 4 }
dot11WNMColocInterfRprtInterfLevel OBJECT-TYPE
SYNTAX Integer32(-128..127)
UNITS "dBm"
MAX-ACCESS read-only
STATUS current
DESCRIPTION
"This is a status variable.
It is written by the SME when a management report is completed.
This attribute contains a signed integer indicating the maximum level of
the collocated interference power in units of dBm over all receive chains
averaged over a 4 s period during an interference period and across interference
bandwidth. When the interference level is unknown, the field is
set to +127 dBm. When the interference level is equal or greater than 126
dBm, the field is set to +126 dBm. If no collocated interference is present
the field is set to -128 dBm. When the interference level is equal or
lower than -127 dBm, the field is set to -127 dBm. The interference level
is referenced to the antenna connector (see definition in Clause 3) used
for reception, like RCPI."
::= { dot11WNMColocInterfReportEntry 5 }
dot11WNMColocInterfRprtInterfAccuracy OBJECT-TYPE
SYNTAX Unsigned32(0..15)
UNITS "dB"
MAX-ACCESS read-only
STATUS current
DESCRIPTION
"This is a status variable.
It is written by the SME when a management report is completed.
This attribute indicates an unsigned integer indicating the expected accuracy
of the estimate of interference in dB with 95% confidence interval.
If the Interference Level field is X (dBm) and the expected accuracy field
is Y (dB), the actual interference level is in the range of [X - Y, X +Y]
with the probability of 95%. If the accuracy is unknown then the Expected
Accuracy field is set to 15."
::= { dot11WNMColocInterfReportEntry 6 }
dot11WNMColocInterfRprtInterfIndex OBJECT-TYPE
SYNTAX Unsigned32(0..15)
MAX-ACCESS read-only
STATUS current
DESCRIPTION
"This is a status variable.
It is written by the SME when a management report is completed.
This attribute indicates the interference index that is unique for each
type of interference source. The field set to 0 indicates that no collocated
interference is present. See 10.23.8 for further details."
::= { dot11WNMColocInterfReportEntry 7 }
dot11WNMColocInterfRprtInterfInterval OBJECT-TYPE
SYNTAX Integer32
UNITS "microseconds"
MAX-ACCESS read-only
STATUS current
DESCRIPTION
"This is a status variable.
It is written by the SME when a management report is completed.
This attribute indicates the interval between two successive periods of
interference in microseconds. When the interval between two successive
periods of interference is variable the field is set to 2E32-1. When the
interval between two successive periods of interference is equal or
greater than 2E32-2 the field is set to 2E32-2. If no collocated interference
is present the field is set to 0."
::= { dot11WNMColocInterfReportEntry 8 }
dot11WNMColocInterfRprtInterfBurstLength OBJECT-TYPE
SYNTAX Integer32
UNITS "microseconds"
MAX-ACCESS read-only
STATUS current
DESCRIPTION
"This is a status variable.
It is written by the SME when a management report is completed.
This attribute indicates the duration of each period of interference in
microseconds. When the duration of each period of interference is variable
the field is set to 2E32-1). When the duration of each period of interference
is equal or greater than 2E32-2, the field is set to 2E32-2. If no
collocated interference is present the field is set to 0."
::= { dot11WNMColocInterfReportEntry 9 }
dot11WNMColocInterfRprtInterfStartTime OBJECT-TYPE
SYNTAX Integer32
MAX-ACCESS read-only
STATUS current
DESCRIPTION
"This is a status variable.
It is written by the SME when a management report is completed.
This attribute contains the least significant 4 octets (i.e. B0-B31) of
the TSF timer at the start of the interference burst. When either the
Interference Interval or the Interference Burst Length fields are set to
2E32-1, this field indicates the average duty cycle. The average duty
cycle value is defined as Round-to-Integer ((2E32-2)[average interference
burst length (microsecond)]/[average interference interval (microsecond)]).
When the interference is nonperiodic the Interference Start Time
field is set to 0. If no collocated interference is present the field is
set to 0."
::= { dot11WNMColocInterfReportEntry 10 }
dot11WNMColocInterfRprtInterfCenterFreq OBJECT-TYPE
SYNTAX Integer32
UNITS "5 kHz"
MAX-ACCESS read-only
STATUS current
DESCRIPTION
"This is a status variable.
It is written by the SME when a management report is completed.
This attribute indicates center frequency of interference in units of 5
kHz. When center frequency is unknown, the center frequency of the STA's
operating channel is reported. If no collocated interference is present
the field is set to 0."
::= { dot11WNMColocInterfReportEntry 11 }
dot11WNMColocInterfRprtInterfBandwidth OBJECT-TYPE
SYNTAX Unsigned32 (0..65535)
UNITS "5 kHz"
MAX-ACCESS read-only
STATUS current
DESCRIPTION
"This is a status variable.
It is written by the SME when a management report is completed.
This attribute indicates the bandwidth at the -3dB roll-off point of the
interference signal in 5 kHz. When bandwidth of the interference signal is
unknown, the field is set to 65 535. When bandwidth of the interference
signal is equal or greater than 65 534 the field is set to 65 534. If no
collocated interference is present the field is set to 0."
::= { dot11WNMColocInterfReportEntry 12 }
-- ********************************************************************
-- * End of dot11WNMColocInterfReport TABLE
-- ********************************************************************
-- ********************************************************************
-- * END of Wireless Network Management Interface MIB
-- ********************************************************************
-- **********************************************************************
-- * END of IEEE 802.11 RM and WNM Interface MIB
-- **********************************************************************
-- **********************************************************************
-- * dot11MeshSTAConfig TABLE
-- **********************************************************************
dot11MeshSTAConfigTable OBJECT-TYPE
SYNTAX SEQUENCE OF Dot11MeshSTAConfigEntry
MAX-ACCESS not-accessible
STATUS current
DESCRIPTION
"Mesh Station Configuration attributes. In tabular form to allow for multiple
instances on an agent."
::= { dot11smt 23 }
dot11MeshSTAConfigEntry OBJECT-TYPE
SYNTAX Dot11MeshSTAConfigEntry
MAX-ACCESS not-accessible
STATUS current
DESCRIPTION
"An entry in the dot11MeshStationConfigTable. It is possible for there to
be multiple IEEE 802.11 interfaces on one agent, each with its unique MAC
address. The relationship between an IEEE 802.11 interface and an interface
in the context of the Internet-standard MIB is one-to-one. As such,
the value of an ifIndex object instance can be directly used to identify
corresponding instances of the objects defined herein.
ifIndex - Each IEEE 802.11 interface is represented by an ifEntry. Interface
tables in this MIB module are indexed by ifIndex."
INDEX { ifIndex }
::= { dot11MeshSTAConfigTable 1 }
Dot11MeshSTAConfigEntry ::=
SEQUENCE {
dot11MeshID OCTET STRING,
dot11MeshNumberOfPeerings Unsigned32,
dot11MeshAcceptingAdditionalPeerings TruthValue,
dot11MeshConnectedToMeshGate TruthValue,
dot11MeshSecurityActivated TruthValue,
dot11MeshActiveAuthenticationProtocol INTEGER,
dot11MeshMaxRetries Unsigned32,
dot11MeshRetryTimeout Unsigned32,
dot11MeshConfirmTimeout Unsigned32,
dot11MeshHoldingTimeout Unsigned32,
dot11MeshConfigGroupUpdateCount Unsigned32,
dot11MeshActivePathSelectionProtocol INTEGER,
dot11MeshActivePathSelectionMetric INTEGER,
dot11MeshForwarding TruthValue,
dot11MeshTTL Unsigned32,
dot11MeshGateAnnouncements TruthValue,
dot11MeshGateAnnouncementInterval Unsigned32,
dot11MeshActiveCongestionControlMode INTEGER,
dot11MeshActiveSynchronizationMethod INTEGER,
dot11MeshNbrOffsetMaxNeighbor Unsigned32,
dot11MBCAActivated TruthValue,
dot11MeshBeaconTimingReportInterval Unsigned32,
dot11MeshBeaconTimingReportMaxNum Unsigned32,
dot11MeshDelayedBeaconTxInterval Unsigned32,
dot11MeshDelayedBeaconTxMaxDelay Unsigned32,
dot11MeshDelayedBeaconTxMinDelay Unsigned32,
dot11MeshAverageBeaconFrameDuration Unsigned32,
dot11MeshSTAMissingAckRetryLimit Unsigned32,
dot11MeshAwakeWindowDuration Unsigned32,
dot11MCCAImplemented TruthValue,
dot11MCCAActivated TruthValue,
dot11MAFlimit Unsigned32,
dot11MCCAScanDuration Unsigned32,
dot11MCCAAdvertPeriodMax Unsigned32,
dot11MCCAMinTrackStates Unsigned32,
dot11MCCAMaxTrackStates Unsigned32,
dot11MCCAOPtimeout Unsigned32,
dot11MCCACWmin Unsigned32,
dot11MCCACWmax Unsigned32,
dot11MCCAAIFSN Unsigned32
}
dot11MeshID OBJECT-TYPE
SYNTAX OCTET STRING (SIZE(0..32))
MAX-ACCESS read-write
STATUS current
DESCRIPTION
"This is a control variable.
It is written by an external management entity.
Changes take effect for the next MLME-START.request.
This attribute reflects the Mesh ID configured in this entity."
::= { dot11MeshSTAConfigEntry 1 }
dot11MeshNumberOfPeerings OBJECT-TYPE
SYNTAX Unsigned32 (0..255)
MAX-ACCESS read-write
STATUS current
DESCRIPTION
"This is a control variable.
It is written by an external management entity.
Changes take effect as soon as practical in the implementation.
This attribute indicates the number of mesh peering currently maintained
by the STA. This value is reflected in the Number of Peerings subfield in
the Mesh Formation Info field in the Mesh Configuration element."
::= { dot11MeshSTAConfigEntry 2 }
dot11MeshAcceptingAdditionalPeerings OBJECT-TYPE
SYNTAX TruthValue
MAX-ACCESS read-write
STATUS current
DESCRIPTION
"This is a control variable.
It is written by an external management entity.
Changes take effect as soon as practical in the implementation.
This attribute indicates whether the station is willing to accept additional
peerings. This value is reflected in the Accepting Additional Mesh
Peerings subfield in the Mesh Capability field in the Mesh Configuration
element."
::= { dot11MeshSTAConfigEntry 3 }
dot11MeshConnectedToMeshGate OBJECT-TYPE
SYNTAX TruthValue
MAX-ACCESS read-write
STATUS current
DESCRIPTION
"This is a control variable.
It is written by an external management entity.
Changes take effect as soon as practical in the implementation.
This attribute indicates whether the station has a mesh path to a mesh
gate. This value is reflected in the Connected to Mesh Gate subfield in
the Mesh Formation Info field in the Mesh Configuration element."
::= { dot11MeshSTAConfigEntry 4 }
dot11MeshSecurityActivated OBJECT-TYPE
SYNTAX TruthValue
MAX-ACCESS read-write
STATUS current
DESCRIPTION
"This is a control variable.
It is written by an external management entity.
Changes take effect for the next MLME-START.request.
This attribute specifies whether the station is security enabled."
::= { dot11MeshSTAConfigEntry 5 }
dot11MeshActiveAuthenticationProtocol OBJECT-TYPE
SYNTAX INTEGER {
null (0),
sae (1),
ieee8021x (2),
vendorSpecific (255) }
MAX-ACCESS read-write
STATUS current
DESCRIPTION
"This is a control variable.
It is written by an external management entity.
Changes take effect for the next MLME-START.request.
This attribute specifies the active authentication protocol."
DEFVAL { null }
::= { dot11MeshSTAConfigEntry 6 }
dot11MeshMaxRetries OBJECT-TYPE
SYNTAX Unsigned32 (0..16)
MAX-ACCESS read-write
STATUS current
DESCRIPTION
"This is a control variable.
It is written by an external management entity.
Changes take effect as soon as practical in the implementation.
This attribute specifies the maximum number of Mesh Peering Open retries
that can be sent to establish a new mesh peering instance in a mesh BSS."
DEFVAL { 2 }
::= { dot11MeshSTAConfigEntry 7 }
dot11MeshRetryTimeout OBJECT-TYPE
SYNTAX Unsigned32 (1..255)
MAX-ACCESS read-write
STATUS current
DESCRIPTION
"This is a control variable.
It is written by an external management entity.
Changes take effect as soon as practical in the implementation.
This attribute specifies the initial retry timeout, in millisecond units,
used by the Mesh Peering Open message."
DEFVAL { 40 }
::= { dot11MeshSTAConfigEntry 8 }
dot11MeshConfirmTimeout OBJECT-TYPE
SYNTAX Unsigned32 (1..255)
MAX-ACCESS read-write
STATUS current
DESCRIPTION
"This is a control variable.
It is written by an external management entity.
Changes take effect as soon as practical in the implementation.
This attribute specifies the initial retry timeout, in millisecond units,
used by the Mesh Peering Open message."
DEFVAL { 40 }
::= { dot11MeshSTAConfigEntry 9 }
dot11MeshHoldingTimeout OBJECT-TYPE
SYNTAX Unsigned32 (1..255)
MAX-ACCESS read-write
STATUS current
DESCRIPTION
"This is a control variable.
It is written by an external management entity.
Changes take effect as soon as practical in the implementation.
This attribute specifies the confirm timeout, in millisecond units, used
by the mesh peering management to close a mesh peering."
DEFVAL { 40 }
::= { dot11MeshSTAConfigEntry 10 }
dot11MeshConfigGroupUpdateCount OBJECT-TYPE
SYNTAX Unsigned32 (1..4294967295)
MAX-ACCESS read-write
STATUS current
DESCRIPTION
"This is a control variable.
It is written by an external management entity.
Changes take effect as soon as practical in the implementation.
This attribute specifies how many times the Mesh Group Key Inform frame
will be retried per mesh group key handshake attempt."
DEFVAL { 3 }
::= { dot11MeshSTAConfigEntry 11 }
dot11MeshActivePathSelectionProtocol OBJECT-TYPE
SYNTAX INTEGER { hwmp (1), vendorSpecific (255) }
MAX-ACCESS read-write
STATUS current
DESCRIPTION
"This is a control variable.
It is written by an external management entity.
Changes take effect for the next MLME-START.request.
This attribute specifies the active path selection protocol."
DEFVAL { hwmp }
::= { dot11MeshSTAConfigEntry 12 }
dot11MeshActivePathSelectionMetric OBJECT-TYPE
SYNTAX INTEGER { airtimeLinkMetric (1), vendorSpecific (255) }
MAX-ACCESS read-write
STATUS current
DESCRIPTION
"This is a control variable.
It is written by an external management entity.
Changes take effect for the next MLME-START.request.
This attribute specifies the active path selection metric."
DEFVAL { airtimeLinkMetric }
::= { dot11MeshSTAConfigEntry 13 }
dot11MeshForwarding OBJECT-TYPE
SYNTAX TruthValue
MAX-ACCESS read-write
STATUS current
DESCRIPTION
"This is a control variable.
It is written by an external management entity.
Changes take effect as soon as practical in the implementation.
This attribute specifies the ability of a mesh STA to forward MSDUs."
DEFVAL { true }
::= { dot11MeshSTAConfigEntry 14 }
dot11MeshTTL OBJECT-TYPE
SYNTAX Unsigned32 (0..255)
MAX-ACCESS read-write
STATUS current
DESCRIPTION
"This is a control variable.
It is written by an external management entity.
Changes take effect as soon as practical in the implementation.
This attribute specifies the value of Mesh TTL subfield set at a source
mesh STA."
DEFVAL { 31 }
::= { dot11MeshSTAConfigEntry 15 }
dot11MeshGateAnnouncements OBJECT-TYPE
SYNTAX TruthValue
MAX-ACCESS read-write
STATUS current
DESCRIPTION
"This is a control variable.
It is written by an external management entity.
Changes take effect as soon as practical in the implementation.
This attribute specifies whether the mesh STA activates mesh gate
announcements."
DEFVAL { false }
::= { dot11MeshSTAConfigEntry 16 }
dot11MeshGateAnnouncementInterval OBJECT-TYPE
SYNTAX Unsigned32 (1..65535)
MAX-ACCESS read-write
STATUS current
DESCRIPTION
"This is a control variable.
It is written by an external management entity.
Changes take effect as soon as practical in the implementation.
This attribute specifies the gate announcement interval. The gate
announcement interval is the number of seconds between the transmission of
two gate announcements."
DEFVAL { 10 }
::= { dot11MeshSTAConfigEntry 17 }
dot11MeshActiveCongestionControlMode OBJECT-TYPE
SYNTAX INTEGER {
null (0),
congestionControlSignaling (1),
vendorSpecific (255) }
MAX-ACCESS read-write
STATUS current
DESCRIPTION
"This is a control variable.
It is written by an external management entity.
Changes take effect for the next MLME-START.request.
This attribute specifies the active congestion control protocol."
DEFVAL { null }
::= { dot11MeshSTAConfigEntry 18 }
dot11MeshActiveSynchronizationMethod OBJECT-TYPE
SYNTAX INTEGER {
neighborOffsetSynchronization (1),
vendorSpecific (255) }
MAX-ACCESS read-write
STATUS current
DESCRIPTION
"This is a control variable.
It is written by an external management entity.
Changes take effect for the next MLME-START.request.
This attribute specifies the MBSS.s active synchronization method."
DEFVAL { neighborOffsetSynchronization }
::= { dot11MeshSTAConfigEntry 19 }
dot11MeshNbrOffsetMaxNeighbor OBJECT-TYPE
SYNTAX Unsigned32 (1..255)
MAX-ACCESS read-only
STATUS current
DESCRIPTION
"This is a capability variable.
Its value is determined by device capabilities.
This attribute specifies the maximum number of neighbor STAs with which
the mesh STA maintains synchronization using the neighbor offset synchronization
method."
DEFVAL { 50 }
::= { dot11MeshSTAConfigEntry 20 }
dot11MBCAActivated OBJECT-TYPE
SYNTAX TruthValue
MAX-ACCESS read-write
STATUS current
DESCRIPTION
"This is a control variable.
It is written by an external management entity.
Changes take effect as soon as practical in the implementation.
This attribute specifies whether the station activates mesh beacon collision
avoidance mechanisms."
DEFVAL { false }
::= { dot11MeshSTAConfigEntry 21 }
dot11MeshBeaconTimingReportInterval OBJECT-TYPE
SYNTAX Unsigned32 (1..255)
MAX-ACCESS read-write
STATUS current
DESCRIPTION
"This is a control variable.
It is written by an external management entity.
This attribute specifies when the Beacon Timing element is present in Beacon
frames. The Beacon Timing element is present when the DTIM Count value
in the Beacon frame is zero or equal to an integer multiple of the set
value."
DEFVAL { 4 }
::= { dot11MeshSTAConfigEntry 22 }
dot11MeshBeaconTimingReportMaxNum OBJECT-TYPE
SYNTAX Unsigned32 (0..50)
MAX-ACCESS read-write
STATUS current
DESCRIPTION
"This is a control variable.
It is written by an external management entity.
Changes take effect as soon as practical in the implementation.
This attribute specifies the maximum number of the Beacon Timing Information
field contained in a Beacon Timing element in the transmitting Beacon
frames."
DEFVAL { 16 }
::= { dot11MeshSTAConfigEntry 23 }
dot11MeshDelayedBeaconTxInterval OBJECT-TYPE
SYNTAX Unsigned32 (0..255)
MAX-ACCESS read-write
STATUS current
DESCRIPTION
"This is a control variable.
It is written by an external management entity.
Changes take effect as soon as practical in the implementation.
This attribute specifies the interval of the delayed beacon transmission
for the purpose of MBCA. The value is expressed in units of Beacon Interval.
The value 0 indicates that the delayed beacon transmission is disabled."
DEFVAL { 0 }
::= { dot11MeshSTAConfigEntry 24 }
dot11MeshDelayedBeaconTxMaxDelay OBJECT-TYPE
SYNTAX Unsigned32 (0..65535)
MAX-ACCESS read-write
STATUS current
DESCRIPTION
"This is a control variable.
It is written by an external management entity.
Changes take effect as soon as practical in the implementation.
This attribute specifies the maximum delay time from a TBTT of delayed
beacon transmissions for the purpose of MBCA. The value is expressed in
units of microseconds."
DEFVAL { 2048 }
::= { dot11MeshSTAConfigEntry 25 }
dot11MeshDelayedBeaconTxMinDelay OBJECT-TYPE
SYNTAX Unsigned32 (0..4023)
MAX-ACCESS read-write
STATUS current
DESCRIPTION
"This is a control variable.
It is written by an external management entity.
Changes take effect as soon as practical in the implementation.
This attribute specifies the minimum delay time from a TBTT of delayed
beacon transmissions for the purpose of MBCA. The value is expressed in
units of microseconds."
DEFVAL { 0 }
::= { dot11MeshSTAConfigEntry 26 }
dot11MeshAverageBeaconFrameDuration OBJECT-TYPE
SYNTAX Unsigned32 (0..16383)
MAX-ACCESS read-write
STATUS current
DESCRIPTION
"This is a control variable.
It is written by an external management entity.
Changes take effect as soon as practical in the implementation.
This attribute specifies the average duration of the last 16 Beacon frames
of other mesh STAs received by this mesh STA. The value is expressed in
units of microseconds."
::= { dot11MeshSTAConfigEntry 27 }
dot11MeshSTAMissingAckRetryLimit OBJECT-TYPE
SYNTAX Unsigned32 (0..100)
MAX-ACCESS read-write
STATUS current
DESCRIPTION
"This is a control variable.
It is written by an external management entity.
Changes take effect as soon as practical in the implementation.
This attribute specifies the number of times the mesh STA may retry a
frame for which it does not receive an ACK for a STA in power save mode
after the mesh STA does not receive an ACK to a directed MPDU sent with
the EOSP set to 1."
::= { dot11MeshSTAConfigEntry 28 }
dot11MeshAwakeWindowDuration OBJECT-TYPE
SYNTAX Unsigned32 (0..65535)
MAX-ACCESS read-write
STATUS current
DESCRIPTION
"This is a control variable.
It is written by an external management entity.
Changes take effect as soon as practical in the implementation.
This attribute specifies the duration of the mesh Awake Window in TUs.
This value is reflected in the value of the Mesh Awake Window element."
::= { dot11MeshSTAConfigEntry 29 }
dot11MCCAImplemented OBJECT-TYPE
SYNTAX TruthValue
MAX-ACCESS read-only
STATUS current
DESCRIPTION
"This is a capability variable.
Its value is determined by device capabilities.
This attribute specifies whether the MCCA is implemented in this station."
::= { dot11MeshSTAConfigEntry 30 }
dot11MCCAActivated OBJECT-TYPE
SYNTAX TruthValue
MAX-ACCESS read-write
STATUS current
DESCRIPTION
"This is a control variable.
It is written by an external management entity.
Changes take effect as soon as practical in the implementation.
This attribute specifies whether the station is MCCA enabled."
DEFVAL { false }
::= { dot11MeshSTAConfigEntry 31 }
dot11MAFlimit OBJECT-TYPE
SYNTAX Unsigned32 (0..255)
MAX-ACCESS read-write
STATUS current
DESCRIPTION
"This is a control variable.
It is written by an external management entity.
Changes take effect as soon as practical in the implementation.
This attribute specifies the maximum MCCA access fraction allowed at the
mesh STA. This number expresses a multiple of (1/255)."
DEFVAL { 128 }
::= { dot11MeshSTAConfigEntry 32 }
dot11MCCAScanDuration OBJECT-TYPE
SYNTAX Unsigned32 (1..65535)
MAX-ACCESS read-write
STATUS current
DESCRIPTION
"This is a control variable.
It is written by an external management entity.
Changes take effect as soon as practical in the implementation.
This attribute specifies the duration in TUs after the activation of MCCA
that the mesh STA shall not initiate or accept MCCAOP Setup Requests."
DEFVAL { 3200 } -- (2 ** 5) * 100
::= { dot11MeshSTAConfigEntry 33 }
dot11MCCAAdvertPeriodMax OBJECT-TYPE
SYNTAX Unsigned32 (0..255)
MAX-ACCESS read-write
STATUS current
DESCRIPTION
"This is a control variable.
It is written by an external management entity.
Changes take effect as soon as practical in the implementation.
This attribute specifies the maximum interval that a mesh STA with
dot11MCCAActivated equal to true waits for an MCCAOP advertisement. It is
expressed in number of DTIM intervals."
DEFVAL { 1 }
::= { dot11MeshSTAConfigEntry 34 }
dot11MCCAMinTrackStates OBJECT-TYPE
SYNTAX Unsigned32 (83..65535)
MAX-ACCESS read-write
STATUS current
DESCRIPTION
"This is a capability variable.
It is written by an external management entity.
Changes take effect as soon as practical in the implementation.
This attribute specifies the smallest number of MCCAOP reservations that
the MAC entity is able to track."
DEFVAL { 83 }
::= { dot11MeshSTAConfigEntry 35 }
dot11MCCAMaxTrackStates OBJECT-TYPE
SYNTAX Unsigned32 (83..65535)
MAX-ACCESS read-write
STATUS current
DESCRIPTION
"This is a control variable.
It is written by an external management entity.
Changes take effect as soon as practical in the implementation.
The lower bound is given by the current value of dot11MCCAMinTrackStates.
This attribute specifies the maximum number of MCCAOP reservations that
the MAC entity is able to track."
DEFVAL { 83 }
::= { dot11MeshSTAConfigEntry 36 }
dot11MCCAOPtimeout OBJECT-TYPE
SYNTAX Unsigned32
MAX-ACCESS read-write
STATUS current
DESCRIPTION
"This is a control variable.
It is written by an external management entity.
Changes take effect as soon as practical in the implementation.
This attribute specifies the timeout value for an MCCAOP teardown. It is
expressed in TU."
DEFVAL { 10000 }
::= { dot11MeshSTAConfigEntry 37 }
dot11MCCACWmin OBJECT-TYPE
SYNTAX Unsigned32 (0..65535)
MAX-ACCESS read-write
STATUS current
DESCRIPTION
"This is a control variable.
It is written by an external management entity.
Changes take effect as soon as practical in the implementation.
This attribute specifies the value of the minimum size of the window that
shall be used by the mesh STA during the MCCAOP for which it is the MCCAOP
owner for generating a random number for the backoff."
DEFVAL { 0 }
::= { dot11MeshSTAConfigEntry 38 }
dot11MCCACWmax OBJECT-TYPE
SYNTAX Unsigned32 (0..65535)
MAX-ACCESS read-write
STATUS current
DESCRIPTION
"This is a control variable.
It is written by an external management entity.
Changes take effect as soon as practical in the implementation.
This attribute specifies the value of the maximum size of the window that
shall be used by the mesh STA during the MCCAOP for which it is the MCCAOP
owner for generating a random number for the backoff. The value of this
attribute shall be such that it could always be expressed in the form of
2**X - 1, where X is an integer."
DEFVAL { 31 }
::= { dot11MeshSTAConfigEntry 39 }
dot11MCCAAIFSN OBJECT-TYPE
SYNTAX Unsigned32 (0..15)
MAX-ACCESS read-write
STATUS current
DESCRIPTION
"This is a control variable.
It is written by an external management entity.
Changes take effect as soon as practical in the implementation.
This attribute specifies the number of slots, after a SIFS duration, that
the mesh STA shall sense the medium idle either before transmitting or
executing a backoff during an MCCAOP for which it is the MCCAOP owner."
DEFVAL { 1 }
::= { dot11MeshSTAConfigEntry 40 }
-- **********************************************************************
-- * End of dot11MeshSTAConfig TABLE
-- **********************************************************************
-- **********************************************************************
-- * dot11MeshHWMPConfig TABLE
-- **********************************************************************
dot11MeshHWMPConfigTable OBJECT-TYPE
SYNTAX SEQUENCE OF Dot11MeshHWMPConfigEntry
MAX-ACCESS not-accessible
STATUS current
DESCRIPTION
"Mesh Station HWMP Configuration attributes. In tabular form to allow for
multiple instances on an agent."
::= { dot11smt 24 }
dot11MeshHWMPConfigEntry OBJECT-TYPE
SYNTAX Dot11MeshHWMPConfigEntry
MAX-ACCESS not-accessible
STATUS current
DESCRIPTION
"An entry in the dot11MeshHWMPConfigTable. It is possible for there to be
multiple IEEE 802.11 interfaces on one agent, each with its unique MAC
address. The relationship between an IEEE 802.11 interface and an interface
in the context of the Internet-standard MIB is one-to-one. As such,
the value of an ifIndex object instance can be directly used to identify
corresponding instances of the objects defined herein.
ifIndex - Each IEEE 802.11 interface is represented by an ifEntry. Interface
tables in this MIB module are indexed by ifIndex."
INDEX { ifIndex }
::= { dot11MeshHWMPConfigTable 1 }
Dot11MeshHWMPConfigEntry ::=
SEQUENCE {
dot11MeshHWMPmaxPREQretries Unsigned32,
dot11MeshHWMPnetDiameter Unsigned32,
dot11MeshHWMPnetDiameterTraversalTime Unsigned32,
dot11MeshHWMPpreqMinInterval Unsigned32,
dot11MeshHWMPperrMinInterval Unsigned32,
dot11MeshHWMPactivePathToRootTimeout Unsigned32,
dot11MeshHWMPactivePathTimeout Unsigned32,
dot11MeshHWMProotMode INTEGER,
dot11MeshHWMProotInterval Unsigned32,
dot11MeshHWMPrannInterval Unsigned32,
dot11MeshHWMPtargetOnly INTEGER,
dot11MeshHWMPmaintenanceInterval Unsigned32,
dot11MeshHWMPconfirmationInterval Unsigned32
}
dot11MeshHWMPmaxPREQretries OBJECT-TYPE
SYNTAX Unsigned32 (0..255)
MAX-ACCESS read-write
STATUS current
DESCRIPTION
"This is a control variable.
It is written by an external management entity.
Changes take effect as soon as practical in the implementation.
This attribute specifies the number of Action frames containing a PREQ
that an originator mesh STA can send to a particular path target for a
specific path discovery."
DEFVAL { 3 }
::= { dot11MeshHWMPConfigEntry 1}
dot11MeshHWMPnetDiameter OBJECT-TYPE
SYNTAX Unsigned32 (1..255)
MAX-ACCESS read-write
STATUS current
DESCRIPTION
"This is a control variable.
It is written by an external management entity.
Changes take effect as soon as practical in the implementation.
This attribute specifies the estimate of the maximum number of hops that
it takes for an HWMP element to propagate across the mesh BSS."
DEFVAL { 31 }
::= { dot11MeshHWMPConfigEntry 2}
dot11MeshHWMPnetDiameterTraversalTime OBJECT-TYPE
SYNTAX Unsigned32 (1..65535)
MAX-ACCESS read-write
STATUS current
DESCRIPTION
"This is a control variable.
It is written by an external management entity.
Changes take effect as soon as practical in the implementation.
This attribute specifies the estimate of the interval of time (in TUs)
that it takes for an HWMP element to propagate across the mesh BSS."
DEFVAL { 500 }
::= { dot11MeshHWMPConfigEntry 3}
dot11MeshHWMPpreqMinInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a mesh STA can send only one Action frame containing a PREQ element."
DEFVAL { 100 }
::= { dot11MeshHWMPConfigEntry 4}
dot11MeshHWMPperrMinInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a mesh STA can send only one Action frame containing a PERR element."
DEFVAL { 100 }
::= { dot11MeshHWMPConfigEntry 5}
dot11MeshHWMPactivePathToRootTimeout OBJECT-TYPE
SYNTAX Unsigned32 (1..65535)
MAX-ACCESS read-write
STATUS current
DESCRIPTION
"This is a control variable.
It is written by an external management entity.
Changes take effect as soon as practical in the implementation.
This object shall specify the time (in TUs) for which mesh STAs receiving
a proactive PREQ shall consider the forwarding information to the root
mesh STA to be valid; it needs to be greater than
dot11MeshHWMProotInterval."
DEFVAL { 5000 }
::= { dot11MeshHWMPConfigEntry 6}
dot11MeshHWMPactivePathTimeout OBJECT-TYPE
SYNTAX Unsigned32 (1..65535)
MAX-ACCESS read-write
STATUS current
DESCRIPTION
"This is a control variable.
It is written by an external management entity.
Changes take effect as soon as practical in the implementation.
This attribute specifies the time (in TUs) for which mesh STAs receiving a
PREQ to individual target(s) shall consider the forwarding information to
be valid."
DEFVAL { 5000 }
::= { dot11MeshHWMPConfigEntry 7}
dot11MeshHWMProotMode OBJECT-TYPE
SYNTAX INTEGER {
noRoot(0),
proactivePREQnoPREP(2),
proactivePREQwithPREP(3),
rann(4) }
MAX-ACCESS read-write
STATUS current
DESCRIPTION
"This is a control variable.
It is written by an external management entity.
Changes take effect as soon as practical in the implementation.
This attribute controls the configuration of a mesh STA as root mesh STA.
A mesh STA is configured as a root mesh STA if dot11MeshHWMProotMode is
set to 2, 3 or 4. Different values correspond to different modes of the
root mesh STA. The mesh STA is not a root mesh STA when the attribute is
set to 0."
DEFVAL { noRoot }
::= { dot11MeshHWMPConfigEntry 8}
dot11MeshHWMProotInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a root mesh STA can send only one Action frame containing a proactive 
PREQ element."
DEFVAL { 2000 }
::= { dot11MeshHWMPConfigEntry 9}
dot11MeshHWMPrannInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a mesh STA can send only one Action frame containing a RANN element."
DEFVAL { 2000 }
::= { dot11MeshHWMPConfigEntry 10}
dot11MeshHWMPtargetOnly OBJECT-TYPE
SYNTAX INTEGER { intermediateMSTA(0), targetOnly(1) }
MAX-ACCESS read-write
STATUS current
DESCRIPTION
"This is a control variable.
It is written by an external management entity.
Changes take effect as soon as practical in the implementation.
This attribute, when set to intermediateMSTA (0), allows intermediate mesh
STAs to respond with a PREP to a PREQ if they have valid forwarding information
to the requested target. When set to targetOnly (1), only the target
mesh STA is allowed to respond with a PREP to a PREQ."
DEFVAL { targetOnly }
::= { dot11MeshHWMPConfigEntry 11}
dot11MeshHWMPmaintenanceInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a mesh STA can send only one Action frame containing a PREQ element
for path maintenance."
DEFVAL { 2000 }
::= { dot11MeshHWMPConfigEntry 12}
dot11MeshHWMPconfirmationInterval OBJECT-TYPE
SYNTAX Unsigned32 (1..65535)
MAX-ACCESS read-write
STATUS current
DESCRIPTION
"This is a control variable.
It is written by an external management entity.
Changes take effect as soon as practical in the implementation.
This attribute specifies the minimum interval of time (in TUs) during
which a mesh STA can send only one Action frame containing a PREQ element
for root path confirmation."
DEFVAL { 2000 }
::= { dot11MeshHWMPConfigEntry 13}
-- ********************************************************************
-- * End of dot11MeshHWMPConfig TABLE
-- ********************************************************************
-- *******************************************************************
-- * dot11RSNAConfigPasswordValue TABLE
-- *******************************************************************
dot11RSNAConfigPasswordValueTable OBJECT-TYPE
SYNTAX SEQUENCE OF Dot11RSNAConfigPasswordValueEntry
MAX-ACCESS not-accessible
STATUS current
DESCRIPTION
"When SAE authentication is the selected AKM suite,
this table is used to locate the binary representation
of a shared, secret, and potentially low-entropy word,
phrase, code, or key that will be used as the
authentication credential between a TA/RA pair.
This table is logically write-only. Reading this table
returns unsuccessful status or null or zero."
::= { dot11smt 25 }
dot11RSNAConfigPasswordValueEntry OBJECT-TYPE
SYNTAX Dot11RSNAConfigPasswordValueEntry
MAX-ACCESS not-accessible
STATUS current
DESCRIPTION
"An entry (conceptual row) in the Password Value Table"
INDEX { dot11RSNAConfigPasswordValueIndex }
::= { dot11RSNAConfigPasswordValueTable 1 }
Dot11RSNAConfigPasswordValueEntry ::=
SEQUENCE {
dot11RSNAConfigPasswordValueIndex Unsigned32,
dot11RSNAConfigPasswordCredential OCTET STRING,
dot11RSNAConfigPasswordPeerMac MacAddress }
dot11RSNAConfigPasswordValueIndex OBJECT-TYPE
SYNTAX Unsigned32
MAX-ACCESS not-accessible
STATUS current
DESCRIPTION
"The auxiliary variable used to identify instances of the columnar
objects in the Password Value table."
::= { dot11RSNAConfigPasswordValueEntry 1 }
dot11RSNAConfigPasswordCredential OBJECT-TYPE
SYNTAX OCTET STRING
MAX-ACCESS read-write
STATUS current
DESCRIPTION
"This is a control variable.
It is written by an external management entity.
Changes take effect as soon as practical in the implementation.
This variable is a binary representation of a shared,
secret, and potentially low-entropy word, phrase, code
or key used as an authentication credential.
Any character-based word or phrase shall be converted
into a canonical binary representation according to
11.3.3 before populating the Password Credential."
::= { dot11RSNAConfigPasswordValueEntry 2 }
dot11RSNAConfigPasswordPeerMac OBJECT-TYPE
SYNTAX MacAddress
MAX-ACCESS read-write
STATUS current
DESCRIPTION
"This is a control variable.
It is written by an external management entity.
Changes take effect as soon as practical in the implementation.
This variable represents the MAC address of the peer
that is to be authenticated. A wildcard BSSID is
permitted when passwords are shared among peers."
::= { dot11RSNAConfigPasswordValueEntry 3 }
-- *******************************************************************
-- * End of dot11RSNAConfigPasswordValue TABLE
-- *******************************************************************
-- *******************************************************************
-- * dot11RSNAConfigDLCGroup TABLE
-- *******************************************************************
dot11RSNAConfigDLCGroupTable OBJECT-TYPE
SYNTAX SEQUENCE OF Dot11RSNAConfigDLCGroupEntry
MAX-ACCESS not-accessible
STATUS current
DESCRIPTION
"This table gives a prioritized list of domain parameter set
Identifiers for discrete logarithm cryptography (DLC) groups."
::= { dot11smt 26 }
dot11RSNAConfigDLCGroupEntry OBJECT-TYPE
SYNTAX Dot11RSNAConfigDLCGroupEntry
MAX-ACCESS not-accessible
STATUS current
DESCRIPTION
"An entry (conceptual row) in the DLC Group Table."
INDEX { dot11RSNAConfigDLCGroupIndex }
::= { dot11RSNAConfigDLCGroupTable 1 }
Dot11RSNAConfigDLCGroupEntry ::=
SEQUENCE {
dot11RSNAConfigDLCGroupIndex Unsigned32,
dot11RSNAConfigDLCGroupIdentifier Unsigned32 }
dot11RSNAConfigDLCGroupIndex OBJECT-TYPE
SYNTAX Unsigned32
MAX-ACCESS not-accessible
STATUS current
DESCRIPTION
"The variable used to identify instances of the columnar
objects in the DLC Group Table. Entries are sorted
based on the Group Index according to the priority
of the Group Identifier relative to other objects.
More preferred Group Identifiers will have a lower
index in the Group Entry."
::= { dot11RSNAConfigDLCGroupEntry 1 }
dot11RSNAConfigDLCGroupIdentifier OBJECT-TYPE
SYNTAX Unsigned32
MAX-ACCESS read-write
STATUS current
DESCRIPTION
"This is a control variable.
It is written by an external management entity.
Changes take effect as soon as practical in the implementation.
This variable uniquely identifies a domain parameter
set for a group in the IANA registry `Group Description'
attributes for RFC 2409 (IKE)."
::= { dot11RSNAConfigDLCGroupEntry 2 }
-- *********************************************************************
-- * End of dot11RSNAConfigDLCGroup TABLE
-- *********************************************************************
-- **********************************************************************
-- * MAC Attribute Templates
-- **********************************************************************
-- **********************************************************************
-- * dot11Operation TABLE
-- **********************************************************************
dot11OperationTable OBJECT-TYPE
SYNTAX SEQUENCE OF Dot11OperationEntry
MAX-ACCESS not-accessible
STATUS current
DESCRIPTION
"Group contains MAC attributes pertaining to the operation of the MAC.
This has been implemented as a table in order to allow for multiple
instantiations on an agent."
::= { dot11mac 1 }
dot11OperationEntry OBJECT-TYPE
SYNTAX Dot11OperationEntry
MAX-ACCESS not-accessible
STATUS current
DESCRIPTION
"An entry in the dot11OperationEntry Table.
ifIndex - Each IEEE 802.11 interface is represented by an ifEntry. Interface
tables in this MIB module are indexed by ifIndex."
INDEX { ifIndex }
::= { dot11OperationTable 1 }
Dot11OperationEntry ::=
SEQUENCE {
dot11MACAddress MacAddress,
dot11RTSThreshold Unsigned32,
dot11ShortRetryLimit Unsigned32,
dot11LongRetryLimit Unsigned32,
dot11FragmentationThreshold Unsigned32,
dot11MaxTransmitMSDULifetime Unsigned32,
dot11MaxReceiveLifetime Unsigned32,
dot11ManufacturerID DisplayString,
dot11ProductID DisplayString,
dot11CAPLimit Unsigned32,
dot11HCCWmin Unsigned32,
dot11HCCWmax Unsigned32,
dot11HCCAIFSN Unsigned32,
dot11ADDBAResponseTimeout Unsigned32,
dot11ADDTSResponseTimeout Unsigned32,
dot11ChannelUtilizationBeaconInterval Unsigned32,
dot11ScheduleTimeout Unsigned32,
dot11DLSResponseTimeout Unsigned32,
dot11QAPMissingAckRetryLimit Unsigned32,
dot11EDCAAveragingPeriod Unsigned32,
dot11HTProtection INTEGER,
dot11RIFSMode TruthValue,
dot11PSMPControlledAccess TruthValue,
dot11ServiceIntervalGranularity Unsigned32,
dot11DualCTSProtection TruthValue,
dot11LSIGTXOPFullProtectionActivated TruthValue,
dot11NonGFEntitiesPresent TruthValue,
dot11PCOActivated TruthValue,
dot11PCOFortyMaxDuration Unsigned32,
dot11PCOTwentyMaxDuration Unsigned32,
dot11PCOFortyMinDuration Unsigned32,
dot11PCOTwentyMinDuration Unsigned32,
dot11FortyMHzIntolerant TruthValue,
dot11BSSWidthTriggerScanInterval Unsigned32,
dot11BSSWidthChannelTransitionDelayFactor Unsigned32,
dot11OBSSScanPassiveDwell Unsigned32,
dot11OBSSScanActiveDwell Unsigned32,
dot11OBSSScanPassiveTotalPerChannel Unsigned32,
dot11OBSSScanActiveTotalPerChannel Unsigned32,
dot112040BSSCoexistenceManagementSupport TruthValue,
dot11OBSSScanActivityThreshold Unsigned32 }
dot11MACAddress OBJECT-TYPE
SYNTAX MacAddress
MAX-ACCESS read-only
STATUS current
DESCRIPTION
"This is a capability variable.
Its value is determined by device capabilities.
Unique MAC Address assigned to the STA."
::= { dot11OperationEntry 1 }
dot11RTSThreshold OBJECT-TYPE
SYNTAX Unsigned32 (0..65536)
MAX-ACCESS read-write
STATUS current
DESCRIPTION
"This is a control variable.
It is written by an external management entity.
Changes take effect as soon as practical in the implementation.
This attribute indicates the number of octets in a PSDU, below which an
RTS/CTS handshake is not performed, except as RTS/CTS is used as a cross
modulation protection mechanism as defined in 9.23. An RTS/CTS handshake
is performed at the beginning of any frame exchange sequence where the
PSDU is of type Data or Management, the PSDU has an individual address in
the Address1 field, and the length of the PSDU is greater than this
threshold. Setting this attribute to be larger than the maximum PSDU size
has the effect of turning off the RTS/CTS handshake for frames of Data or
Management type transmitted by this STA. Setting this attribute to 0 has
the effect of turning on the RTS/CTS handshake for all frames of Data or
Management type transmitted by this STA."
DEFVAL { 65536 }
::= { dot11OperationEntry 2 }
dot11ShortRetryLimit OBJECT-TYPE
SYNTAX Unsigned32 (1..255)
MAX-ACCESS read-write
STATUS current
DESCRIPTION
"This is a control variable.
It is written by an external management entity.
Changes take effect as soon as practical in the implementation.
This attribute indicates the maximum number of transmission attempts of a
frame, the length of which is less than or equal to dot11RTSThreshold,
that is made before a failure condition is indicated."
DEFVAL { 7 }
::= { dot11OperationEntry 3 }
dot11LongRetryLimit OBJECT-TYPE
SYNTAX Unsigned32 (1..255)
MAX-ACCESS read-write
STATUS current
DESCRIPTION
"This is a control variable.
It is written by an external management entity.
Changes take effect as soon as practical in the implementation.
This attribute indicates the maximum number of transmission attempts of a
frame, the length of which is greater than dot11RTSThreshold, that is made
before a failure condition is indicated."
DEFVAL { 4 }
::= { dot11OperationEntry 4 }
dot11FragmentationThreshold OBJECT-TYPE
SYNTAX Unsigned32 (256..8000)
MAX-ACCESS read-write
STATUS current
DESCRIPTION
"This is a control variable.
It is written by an external management entity.
Changes take effect as soon as practical in the implementation.
This attribute specifies the current maximum size, in octets, of the MPDU
that may be delivered to the security encapsulation. This maximum size
does not apply when an MSDU is transmitted using an HT-immediate or HTdelayed
Block Ack agreement, or when an MSDU or MMPDU is carried in an AMPDU.
Fields added to the frame by security encapsulation are not counted
against the limit specified by this attribute. Except as described above,
an MSDU or MMPDU is fragmented when the resulting frame has an individual
address in the Address1 field, and the length of the frame is larger than
this threshold, excluding security encapsulation fields. The default value
for this attribute is the lesser of 8000 or the aMPDUMaxLength or the aPSDUMaxLength
of the attached PHY and the value never exceeds the lesser of
8000 or the aMPDUMaxLength or the aPSDUMaxLength of the attached PHY."
::= { dot11OperationEntry 5 }
dot11MaxTransmitMSDULifetime OBJECT-TYPE
SYNTAX Unsigned32 (1..4294967295)
MAX-ACCESS read-write
STATUS current
DESCRIPTION
"This is a control variable.
It is written by an external management entity.
Changes take effect as soon as practical in the implementation.
The MaxTransmitMSDULifetime is the elapsed time in TU, after the initial
transmission of an MSDU, after which further attempts to transmit the MSDU
are terminated."
DEFVAL { 512 }
::= { dot11OperationEntry 6 }
dot11MaxReceiveLifetime OBJECT-TYPE
SYNTAX Unsigned32 (1..4294967295)
MAX-ACCESS read-write
STATUS current
DESCRIPTION
"This is a control variable.
It is written by an external management entity.
Changes take effect as soon as practical in the implementation.
The MaxReceiveLifetime is the elapsed time in TU, after the initial reception
of a fragmented MMPDU or MSDU, after which further attempts to reassemble
the MMPDU or MSDU are terminated."
DEFVAL { 512 }
::= { dot11OperationEntry 7 }
dot11ManufacturerID OBJECT-TYPE
SYNTAX DisplayString (SIZE(0..128))
MAX-ACCESS read-only
STATUS current
DESCRIPTION
"This is a capability variable.
Its value is determined by device capabilities.
The ManufacturerID includes, at a minimum, the name of the manufacturer.
It may include additional information at the manufacturer's discretion.
The default value of this attribute is null."
::= { dot11OperationEntry 8 }
dot11ProductID OBJECT-TYPE
SYNTAX DisplayString (SIZE(0..128))
MAX-ACCESS read-only
STATUS current
DESCRIPTION
"This is a capability variable.
Its value is determined by device capabilities.
The ProductID includes, at a minimum, an identifier that is unique to the
manufacturer. It may include additional information at the manufacturer's
discretion. The default value of this attribute is null."
::= { dot11OperationEntry 9 }
dot11CAPLimit OBJECT-TYPE
SYNTAX Unsigned32
MAX-ACCESS read-write
STATUS current
DESCRIPTION
"This is a control variable.
It is written by an external management entity.
Changes take effect as soon as practical in the implementation.
This attribute specifies the maximum number of TUs a Controlled access
phase(CAP) can last."
::= { dot11OperationEntry 10 }
dot11HCCWmin OBJECT-TYPE
SYNTAX Unsigned32 -- (0..aCWmin)
MAX-ACCESS read-write
STATUS current
DESCRIPTION
"This is a control variable.
It is written by an external management entity.
Changes take effect as soon as practical in the implementation.
This attribute specifies the value of the minimum size of the window that
is used by the HC for generating a random number for the backoff. The
value of this attribute is such that it could always be expressed in the
form of 2**X - 1, where X is an integer."
DEFVAL { 0 }
::= { dot11OperationEntry 11 }
dot11HCCWmax OBJECT-TYPE
SYNTAX Unsigned32 -- (0..aCWmax)
MAX-ACCESS read-write
STATUS current
DESCRIPTION
"This is a control variable.
It is written by an external management entity.
Changes take effect as soon as practical in the implementation.
This attribute specifies the value of the maximum size of the window that
is used by the HC for generating a random number for the backoff. The
value of this attribute is such that it could always be expressed in the
form of 2**X - 1, where X is an integer."
DEFVAL { 0 }
::= { dot11OperationEntry 12 }
dot11HCCAIFSN OBJECT-TYPE
SYNTAX Unsigned32 (1..15)
MAX-ACCESS read-write
STATUS current
DESCRIPTION
"This is a control variable.
It is written by an external management entity.
Changes take effect as soon as practical in the implementation.
This attribute specifies the number of slots, after a SIFS duration, that
the HC senses the medium idle either before transmitting or executing a
backoff."
DEFVAL { 1 }
::= { dot11OperationEntry 13 }
dot11ADDBAResponseTimeout OBJECT-TYPE
SYNTAX Unsigned32 (1..65535)
MAX-ACCESS read-write
STATUS current
DESCRIPTION
"This is a control variable.
It is written by an external management entity.
Changes take effect as soon as practical in the implementation.
This attribute specifies the timeout in seconds for an ADDBA Response
frame that is a response to an ADDBA Request frame."
DEFVAL { 1 }
::= { dot11OperationEntry 14 }
dot11ADDTSResponseTimeout OBJECT-TYPE
SYNTAX Unsigned32 (1..65535)
MAX-ACCESS read-write
STATUS current
DESCRIPTION
"This is a control variable.
It is written by an external management entity.
Changes take effect as soon as practical in the implementation.
This attribute specifies the maximum number of seconds an ADDTS request is
to be responded."
DEFVAL { 1 }
::= { dot11OperationEntry 15 }
dot11ChannelUtilizationBeaconInterval OBJECT-TYPE
SYNTAX Unsigned32 (1..100)
MAX-ACCESS read-write
STATUS current
DESCRIPTION
"This is a control variable.
It is written by an external management entity.
Changes take effect as soon as practical in the implementation.
This attribute indicates the number of beacon intervals over which the
channel busy time should be averaged."
DEFVAL { 50 }
::= { dot11OperationEntry 16 }
dot11ScheduleTimeout OBJECT-TYPE
SYNTAX Unsigned32 (1..100)
MAX-ACCESS read-write
STATUS current
DESCRIPTION
"This is a control variable.
It is written by an external management entity.
Changes take effect as soon as practical in the implementation.
This attribute indicates the duration in TUs after which a STA could go
into power save mode."
DEFVAL { 10 }
::= { dot11OperationEntry 17 }
dot11DLSResponseTimeout OBJECT-TYPE
SYNTAX Unsigned32 (1..65535)
MAX-ACCESS read-write
STATUS current
DESCRIPTION
"This is a control variable.
It is written by an external management entity.
Changes take effect as soon as practical in the implementation.
This attribute specifies the maximum number of seconds a direct link
request is to be responded."
DEFVAL { 10 }
::= { dot11OperationEntry 18 }
dot11QAPMissingAckRetryLimit OBJECT-TYPE
SYNTAX Unsigned32 (1..100)
MAX-ACCESS read-write
STATUS current
DESCRIPTION
"This is a control variable.
It is written by an external management entity.
Changes take effect as soon as practical in the implementation.
This attribute indicates the number of times the AP may retry a frame for
which it does not receive an ACK for a STA in power save mode after
receiving a PS-Poll and sending an individually addressed response or
after the AP does not receive an ACK to a directed MPDU sent with the EOSP
equal to 1."
::= { dot11OperationEntry 19 }
dot11EDCAAveragingPeriod OBJECT-TYPE
SYNTAX Unsigned32 (1..100)
MAX-ACCESS read-write
STATUS current
DESCRIPTION
"This is a control variable.
It is written by an external management entity.
Changes take effect as soon as practical in the implementation.
This attribute indicates the number of seconds over which the
admitted_time and used_time are computed."
DEFVAL { 5 }
::= { dot11OperationEntry 20 }
dot11HTProtection OBJECT-TYPE
SYNTAX INTEGER {
htNoProtection (0),
htNonmemberProtection(1),
ht20MHzProtection(2),
htNonHTmixed(3) }
MAX-ACCESS read-write
STATUS current
DESCRIPTION
"This is a control variable.
It is written by an external management entity.
Changes take effect as soon as practical in the implementation.
This attribute indicates the level of protection that needs to be provided
to the transmissions in an IEEE 802.11 network with HT STAs."
DEFVAL { htNoProtection }
::= { dot11OperationEntry 21 }
dot11RIFSMode OBJECT-TYPE
SYNTAX TruthValue
MAX-ACCESS read-write
STATUS current
DESCRIPTION
"This is a control variable.
It is written by an external management entity.
Changes take effect as soon as practical in the implementation.
This attribute, when true, indicates that use of RIFS is allowed in the
BSS."
DEFVAL { false }
::= { dot11OperationEntry 22 }
dot11PSMPControlledAccess OBJECT-TYPE
SYNTAX TruthValue
MAX-ACCESS read-write
STATUS current
DESCRIPTION
"This is a control variable.
It is written by an external management entity.
Changes take effect as soon as practical in the implementation.
This attribute, when true indicates that the AP accepts associations only
from STAs for which dot11PSMPOptionImplemented is true."
DEFVAL { false }
::= { dot11OperationEntry 23 }
dot11ServiceIntervalGranularity OBJECT-TYPE
SYNTAX Unsigned32 (0..7)
MAX-ACCESS read-write
STATUS current
DESCRIPTION
"This is a control variable.
It is written by an external management entity.
Changes take effect as soon as practical in the implementation.
This attribute indicates the SI granularity to be used for scheduled PSMP.
The value of the granularity is given by
(dot11ServiceIntervalGranularity+1)*5 ms."
DEFVAL { 0 }
::= { dot11OperationEntry 24 }
dot11DualCTSProtection OBJECT-TYPE
SYNTAX TruthValue
MAX-ACCESS read-write
STATUS current
DESCRIPTION
"This is a control variable.
It is written by an external management entity.
Changes take effect as soon as practical in the implementation.
This attribute, when true indicates that the AP uses dual CTS protection
to protect the non-STBC frame and STBC frame transmissions."
DEFVAL { false }
::= { dot11OperationEntry 25 }
dot11LSIGTXOPFullProtectionActivated OBJECT-TYPE
SYNTAX TruthValue
MAX-ACCESS read-write
STATUS current
DESCRIPTION
"This is a control variable.
It is written by an external management entity.
Changes take effect as soon as practical in the implementation.
This attribute, when true, indicates that the LSIG TXOP protection may be
used by STAs that have the attribute
dot11LSigTxopProtectionOptionImplemented equal to true."
DEFVAL { false }
::= { dot11OperationEntry 26 }
dot11NonGFEntitiesPresent OBJECT-TYPE
SYNTAX TruthValue
MAX-ACCESS read-only
STATUS current
DESCRIPTION
"This is a status variable.
It is written by the SME when it determines that the presence of greenfield
stations in the BSS has changed.
This attribute, when true, indicates that STA that are not HT-greenfield
Capable are present in the BSS."
DEFVAL { false }
::= { dot11OperationEntry 27 }
dot11PCOActivated OBJECT-TYPE
SYNTAX TruthValue
MAX-ACCESS read-write
STATUS current
DESCRIPTION
"This is a control variable.
It is written by an external management entity.
Changes take effect as soon as practical in the implementation.
This attribute, when true, indicates that the PCO is activated."
DEFVAL { false }
::= { dot11OperationEntry 28 }
dot11PCOFortyMaxDuration OBJECT-TYPE
SYNTAX Unsigned32 (1..200)
MAX-ACCESS read-write
STATUS current
DESCRIPTION
"This is a control variable.
It is written by an external management entity.
Changes take effect as soon as practical in the implementation.
The attribute indicates the maximum duration of 40 MHz phase in TU under
PCO operation. The value of this attribute shall be equal to or larger
than dot11PCOFortyMinDuration."
DEFVAL { 30 }
::= { dot11OperationEntry 29 }
dot11PCOTwentyMaxDuration OBJECT-TYPE
SYNTAX Unsigned32 (1..200)
MAX-ACCESS read-write
STATUS current
DESCRIPTION
"This is a control variable.
It is written by an external management entity.
Changes take effect as soon as practical in the implementation.
The attribute indicates the maximum duration of 20 MHz phase in TU under
PCO operation. The value of this attribute shall be equal to or larger
than dot11PCOTwentyMinDuration."
DEFVAL { 30 }
::= { dot11OperationEntry 30 }
dot11PCOFortyMinDuration OBJECT-TYPE
SYNTAX Unsigned32 (1..200)
MAX-ACCESS read-write
STATUS current
DESCRIPTION
"This is a control variable.
It is written by an external management entity.
Changes take effect as soon as practical in the implementation.
The attribute indicates the minimum duration of 40 MHz phase in TU under
PCO operation."
DEFVAL { 20 }
::= { dot11OperationEntry 31 }
dot11PCOTwentyMinDuration OBJECT-TYPE
SYNTAX Unsigned32 (1..200)
MAX-ACCESS read-write
STATUS current
DESCRIPTION
"This is a control variable.
It is written by an external management entity.
Changes take effect as soon as practical in the implementation.
The attribute indicates the minimum duration of 20 MHz phase in TU under
PCO operation."
DEFVAL { 20 }
::= { dot11OperationEntry 32 }
dot11FortyMHzIntolerant OBJECT-TYPE
SYNTAX TruthValue
MAX-ACCESS read-write
STATUS current
DESCRIPTION
"This is a control variable.
It is written by an external management entity.
Changes take effect as soon as practical in the implementation.
This attribute, when true, indicates that the STA requests that 40 MHz
mask PPDUs are not transmitted within range of the STA."
DEFVAL { false }
::= { dot11OperationEntry 33 }
dot11BSSWidthTriggerScanInterval OBJECT-TYPE
SYNTAX Unsigned32 (10..900)
MAX-ACCESS read-write
STATUS current
DESCRIPTION
"This is a control variable.
It is written by an external management entity.
Changes take effect as soon as practical in the implementation.
This attribute indicates the maximum interval in seconds between scan
operations to be performed to detect BSS channel width trigger events."
DEFVAL { 300 }
::= { dot11OperationEntry 34 }
dot11BSSWidthChannelTransitionDelayFactor OBJECT-TYPE
SYNTAX Unsigned32 (5..100)
MAX-ACCESS read-write
STATUS current
DESCRIPTION
"This is a control variable.
It is written by an external management entity.
Changes take effect as soon as practical in the implementation.
This attribute indicates the minimum ratio between the delay time in performing
a switch from 20 MHz BSS operation to 20/40 MHz BSS operation and
the maximum interval between OBSS scan operations."
DEFVAL { 5 }
::= { dot11OperationEntry 35 }
dot11OBSSScanPassiveDwell OBJECT-TYPE
SYNTAX Unsigned32 (5..1000)
MAX-ACCESS read-write
STATUS current
DESCRIPTION
"This is a control variable.
It is written by an external management entity.
Changes take effect as soon as practical in the implementation.
This attribute indicates the minimum amount of time in TU that the STA
continuously scans each channel when performing a passive OBSS scan operation."
DEFVAL { 20 }
::= { dot11OperationEntry 36 }
dot11OBSSScanActiveDwell OBJECT-TYPE
SYNTAX Unsigned32 (10..1000)
MAX-ACCESS read-write
STATUS current
DESCRIPTION
"This is a control variable.
It is written by an external management entity.
Changes take effect as soon as practical in the implementation.
This attribute indicates the minimum amount of time in TU that the STA
continuously scans each channel when performing an active OBSS scan operation."
DEFVAL { 10 }
::= { dot11OperationEntry 37 }
dot11OBSSScanPassiveTotalPerChannel OBJECT-TYPE
SYNTAX Unsigned32 (200..10000)
MAX-ACCESS read-write
STATUS current
DESCRIPTION
"This is a control variable.
It is written by an external management entity.
Changes take effect as soon as practical in the implementation.
This attribute indicates the minimum total amount of time in TU that the
STA scans each channel when performing a passive OBSS scan operation."
DEFVAL { 200 }
::= { dot11OperationEntry 38 }
dot11OBSSScanActiveTotalPerChannel OBJECT-TYPE
SYNTAX Unsigned32 (20..10000)
MAX-ACCESS read-write
STATUS current
DESCRIPTION
"This is a control variable.
It is written by an external management entity.
Changes take effect as soon as practical in the implementation.
This attribute indicates the minimum total amount of time in TU that the
STA scans each channel when performing an active OBSS scan operation."
DEFVAL { 20 }
::= { dot11OperationEntry 39 }
dot112040BSSCoexistenceManagementSupport OBJECT-TYPE
SYNTAX TruthValue
MAX-ACCESS read-only
STATUS current
DESCRIPTION
"This is a capability variable.
Its value is determined by device capabilities.
This attribute, when true, indicates that the STA supports the transmission
and reception of the 20/40 BSS Coexistence Management frame."
DEFVAL { false }
::= { dot11OperationEntry 40 }
dot11OBSSScanActivityThreshold OBJECT-TYPE
SYNTAX Unsigned32 (0..100)
MAX-ACCESS read-write
STATUS current
DESCRIPTION
"This is a control variable.
It is written by an external management entity.
Changes take effect as soon as practical in the implementation.
This attribute indicates in hundredths of percent, the maximum total time
that a STA may be active on the medium during a period of
dot11BSSWidthChannelTransitionDelayFactor *
dot11BSSWidthTriggerScanInterval seconds without being obligated to perform
OBSS Scan operations. The default value of this attribute is 25,
which equates to 0.25%."
DEFVAL { 25 }
::= { dot11OperationEntry 41}
-- **********************************************************************
-- * End of dot11Operation TABLE
-- **********************************************************************
-- **********************************************************************
-- * dot11Counters TABLE
-- **********************************************************************
dot11CountersTable OBJECT-TYPE
SYNTAX SEQUENCE OF Dot11CountersEntry
MAX-ACCESS not-accessible
STATUS current
DESCRIPTION
"Group containing attributes that are MAC counters. Implemented as a table
to allow for multiple instantiations on an agent."
::= { dot11mac 2 }
dot11CountersEntry OBJECT-TYPE
SYNTAX Dot11CountersEntry
MAX-ACCESS not-accessible
STATUS current
DESCRIPTION
"An entry in the dot11CountersEntry Table.
ifIndex - Each IEEE 802.11 interface is represented by an ifEntry. Interface
tables in this MIB module are indexed by ifIndex."
INDEX { ifIndex }
::= { dot11CountersTable 1 }
Dot11CountersEntry ::=
SEQUENCE {
dot11TransmittedFragmentCount Counter32,
dot11GroupTransmittedFrameCount Counter32,
dot11FailedCount Counter32,
dot11RetryCount Counter32,
dot11MultipleRetryCount Counter32,
dot11FrameDuplicateCount Counter32,
dot11RTSSuccessCount Counter32,
dot11RTSFailureCount Counter32,
dot11ACKFailureCount Counter32,
dot11ReceivedFragmentCount Counter32,
dot11GroupReceivedFrameCount Counter32,
dot11FCSErrorCount Counter32,
dot11TransmittedFrameCount Counter32,
dot11WEPUndecryptableCount Counter32,
dot11QosDiscardedFragmentCount Counter32,
dot11AssociatedStationCount Counter32,
dot11QosCFPollsReceivedCount Counter32,
dot11QosCFPollsUnusedCount Counter32,
dot11QosCFPollsUnusableCount Counter32,
dot11QosCFPollsLostCount Counter32,
dot11TransmittedAMSDUCount Counter32,
dot11FailedAMSDUCount Counter32,
dot11RetryAMSDUCount Counter32,
dot11MultipleRetryAMSDUCount Counter32,
dot11TransmittedOctetsInAMSDUCount Counter64,
dot11AMSDUAckFailureCount Counter32,
dot11ReceivedAMSDUCount Counter32,
dot11ReceivedOctetsInAMSDUCount Counter64,
dot11TransmittedAMPDUCount Counter32,
dot11TransmittedMPDUsInAMPDUCount Counter32,
dot11TransmittedOctetsInAMPDUCount Counter64,
dot11AMPDUReceivedCount Counter32,
dot11MPDUInReceivedAMPDUCount Counter32,
dot11ReceivedOctetsInAMPDUCount Counter64,
dot11AMPDUDelimiterCRCErrorCount Counter32,
dot11ImplicitBARFailureCount Counter32,
dot11ExplicitBARFailureCount Counter32,
dot11ChannelWidthSwitchCount Counter32,
dot11TwentyMHzFrameTransmittedCount Counter32,
dot11FortyMHzFrameTransmittedCount Counter32,
dot11TwentyMHzFrameReceivedCount Counter32,
dot11FortyMHzFrameReceivedCount Counter32,
dot11PSMPUTTGrantDuration Counter32,
dot11PSMPUTTUsedDuration Counter32,
dot11GrantedRDGUsedCount Counter32,
dot11GrantedRDGUnusedCount Counter32,
dot11TransmittedFramesInGrantedRDGCount Counter32,
dot11TransmittedOctetsInGrantedRDGCount Counter64,
dot11BeamformingFrameCount Counter32,
dot11DualCTSSuccessCount Counter32,
dot11DualCTSFailureCount Counter32,
dot11STBCCTSSuccessCount Counter32,
dot11STBCCTSFailureCount Counter32,
dot11nonSTBCCTSSuccessCount Counter32,
dot11nonSTBCCTSFailureCount Counter32,
dot11RTSLSIGSuccessCount Counter32,
dot11RTSLSIGFailureCount Counter32,
dot11PBACErrors Counter32,
dot11DeniedAssociationCounterDueToBSSLoad Counter32
}
dot11TransmittedFragmentCount OBJECT-TYPE
SYNTAX Counter32
MAX-ACCESS read-only
STATUS current
DESCRIPTION
"This is a status variable.
It is written by the MAC when a fragment is successfully transmitted.
This counter is incremented for an acknowledged MPDU with an individual
address in the address 1 field or an MPDU with a group address in the
address 1 field of type Data or Management."
::= { dot11CountersEntry 1 }
dot11GroupTransmittedFrameCount OBJECT-TYPE
SYNTAX Counter32
MAX-ACCESS read-only
STATUS current
DESCRIPTION
"This is a status variable.
It is written by the MAC when a group addressed frame is transmitted.
This counter is incremented only when the group bit is set in the destination
MAC address of a successfully transmitted MSDU. When operating as a
STA in an ESS, where these frames are directed to the AP, this implies
having received an acknowledgment to all associated MPDUs."
::= { dot11CountersEntry 2 }
dot11FailedCount OBJECT-TYPE
SYNTAX Counter32
MAX-ACCESS read-only
STATUS current
DESCRIPTION
"This is a status variable.
It is written by the MAC when the condition described below occurs.
This counter increments when an MSDU is not transmitted successfully due
to the number of transmit attempts exceeding either the
dot11ShortRetryLimit or dot11LongRetryLimit."
::= { dot11CountersEntry 3 }
dot11RetryCount OBJECT-TYPE
SYNTAX Counter32
MAX-ACCESS read-only
STATUS current
DESCRIPTION
"This is a status variable.
It is written by the MAC when the condition described below occurs.
This counter increments when an MSDU is successfully transmitted after one
or more retransmissions."
::= { dot11CountersEntry 4 }
dot11MultipleRetryCount OBJECT-TYPE
SYNTAX Counter32
MAX-ACCESS read-only
STATUS current
DESCRIPTION
"This is a status variable.
It is written by the MAC when the condition described below occurs.
This counter increments when an MSDU is successfully transmitted after
more than one retransmission."
::= { dot11CountersEntry 5 }
dot11FrameDuplicateCount OBJECT-TYPE
SYNTAX Counter32
MAX-ACCESS read-only
STATUS current
DESCRIPTION
"This is a status variable.
It is written by the MAC when the condition described below occurs.
This counter increments when a frame is received that the Sequence Control
field indicates is a duplicate."
::= { dot11CountersEntry 6 }
dot11RTSSuccessCount OBJECT-TYPE
SYNTAX Counter32
MAX-ACCESS read-only
STATUS current
DESCRIPTION
"This is a status variable.
It is written by the MAC when a CTS is received in response to an RTS.
This counter increments when a CTS is received in response to an RTS."
::= { dot11CountersEntry 7 }
dot11RTSFailureCount OBJECT-TYPE
SYNTAX Counter32
MAX-ACCESS read-only
STATUS current
DESCRIPTION
"This is a status variable.
It is written by the MAC when the condition described below occurs.
This counter increments when a CTS is not received in response to an RTS."
::= { dot11CountersEntry 8 }
dot11ACKFailureCount OBJECT-TYPE
SYNTAX Counter32
MAX-ACCESS read-only
STATUS current
DESCRIPTION
"This is a status variable.
It is written by the MAC when the condition described below occurs.
This counter increments when an ACK is not received when expected."
::= { dot11CountersEntry 9 }
dot11ReceivedFragmentCount OBJECT-TYPE
SYNTAX Counter32
MAX-ACCESS read-only
STATUS current
DESCRIPTION
"This is a status variable.
It is written by the MAC when a fragment is successfully received.
This counter is incremented for each successfully received MPDU of type
Data or Management."
::= { dot11CountersEntry 10 }
dot11GroupReceivedFrameCount OBJECT-TYPE
SYNTAX Counter32
MAX-ACCESS read-only
STATUS current
DESCRIPTION
"This is a status variable.
It is written by the MAC when a group addressed frame is received.
This counter increments when a MSDU is received with the group bit set in
the destination MAC address."
::= { dot11CountersEntry 11 }
dot11FCSErrorCount OBJECT-TYPE
SYNTAX Counter32
MAX-ACCESS read-only
STATUS current
DESCRIPTION
"This is a status variable.
It is written by the MAC when the condition described below occurs.
This counter increments when an FCS error is detected in a received MPDU."
::= { dot11CountersEntry 12 }
dot11TransmittedFrameCount OBJECT-TYPE
SYNTAX Counter32
MAX-ACCESS read-only
STATUS current
DESCRIPTION
"This is a status variable.
It is written by the MAC when a frame is successfully transmitted.
This counter increments for each successfully transmitted MSDU."
::= { dot11CountersEntry 13 }
dot11WEPUndecryptableCount OBJECT-TYPE
SYNTAX Counter32
MAX-ACCESS read-only
STATUS current
DESCRIPTION
"This is a status variable.
It is written by the MAC when the condition described below occurs.
This counter increments when a frame is received with the Protected Frame
subfield of the Frame Control field equal to one and the WEPOn value for
the key mapped to the transmitter's MAC address indicates that the frame
should not have been encrypted or that frame is discarded due to the
receiving STA not implementing the privacy option."
::= { dot11CountersEntry 14 }
dot11QosDiscardedFragmentCount OBJECT-TYPE
SYNTAX Counter32
MAX-ACCESS read-only
STATUS current
DESCRIPTION
"This is a status variable.
It is written by the MAC when the condition described below occurs.
This counter increments for each QoS Data MPDU that has been discarded."
::= { dot11CountersEntry 15 }
dot11AssociatedStationCount OBJECT-TYPE
SYNTAX Counter32
MAX-ACCESS read-only
STATUS current
DESCRIPTION
"This is a status variable.
It is written by the MAC when a STA associates or disassociates.
This counter, only available at AP, increments when a station associates
or reassociates. This counter decrements when a station disassociates."
::= { dot11CountersEntry 16 }
dot11QosCFPollsReceivedCount OBJECT-TYPE
SYNTAX Counter32
MAX-ACCESS read-only
STATUS current
DESCRIPTION
"This is a status variable.
It is written by the MAC when a CF-Poll is received.
This counter increments for each QoS (+)CF-Poll that has been received."
::= { dot11CountersEntry 17 }
dot11QosCFPollsUnusedCount OBJECT-TYPE
SYNTAX Counter32
MAX-ACCESS read-only
STATUS current
DESCRIPTION
"This is a status variable.
It is written by the MAC when a CF-Poll is unused.
This counter increments for each QoS (+)CF-Poll that has been received but
not used."
::= { dot11CountersEntry 18 }
dot11QosCFPollsUnusableCount OBJECT-TYPE
SYNTAX Counter32
MAX-ACCESS read-only
STATUS current
DESCRIPTION
"This is a status variable.
It is written by the MAC when the condition described below occurs.
This counter increments for each QoS (+)CF-Poll that has been received but
could not be used due to the TXOP size being smaller than the time that is
required for one frame exchange sequence."
::= { dot11CountersEntry 19 }
dot11QosCFPollsLostCount OBJECT-TYPE
SYNTAX Counter32
MAX-ACCESS read-only
STATUS current
DESCRIPTION
"This is a status variable.
It is written by the MAC when the condition described below occurs.
This counter increments for each QoS (+)CF-Poll that has been issued where
there was no response from the QoS STA."
::= { dot11CountersEntry 20 }
dot11TransmittedAMSDUCount OBJECT-TYPE
SYNTAX Counter32
MAX-ACCESS read-only
STATUS current
DESCRIPTION
"This is a status variable.
It is written by the MAC when a transmitted A-MSDU is acknowledged.
This counter shall be incremented for an acknowledged A-MSDU frame with an
individual address in the address 1 field or an A-MSDU frame with a group
address in the address 1 field."
::= { dot11CountersEntry 21 }
dot11FailedAMSDUCount OBJECT-TYPE
SYNTAX Counter32
MAX-ACCESS read-only
STATUS current
DESCRIPTION
"This is a status variable.
It is written by the MAC when the condition described below occurs.
This counter shall be incremented when an A-MSDU is not transmitted successfully
due to the number of transmit attempts exceeding either the
dot11ShortRetryLimit or dot11LongRetryLimit."
::= { dot11CountersEntry 22 }
dot11RetryAMSDUCount OBJECT-TYPE
SYNTAX Counter32
MAX-ACCESS read-only
STATUS current
DESCRIPTION
"This is a status variable.
It is written by the MAC when a transmitted A-MSDU is acknowledged only
after one or more retransmissions.
This counter shall be incremented when an A-MSDU is successfully transmitted
after one or more retransmissions."
::= { dot11CountersEntry 23 }
dot11MultipleRetryAMSDUCount OBJECT-TYPE
SYNTAX Counter32
MAX-ACCESS read-only
STATUS current
DESCRIPTION
"This is a status variable.
It is written by the MAC when a transmitted A-MSDU is acknowledged only
after more than one retransmission.
This counter shall be incremented when an A-MSDU is successfully transmitted
after more than one retransmission."
::= { dot11CountersEntry 24 }
dot11TransmittedOctetsInAMSDUCount OBJECT-TYPE
SYNTAX Counter64
MAX-ACCESS read-only
STATUS current
DESCRIPTION
"This is a status variable.
It is written by the MAC when an A-MSDU is transmitted.
This counter shall be incremented by the number of octets in the framebody
of an A-MSDU frame when an A-MSDU frame is successfully transmitted."
::= { dot11CountersEntry 25 }
dot11AMSDUAckFailureCount OBJECT-TYPE
SYNTAX Counter32
MAX-ACCESS read-only
STATUS current
DESCRIPTION
"This is a status variable.
It is written by the MAC when the condition described below occurs.
This counter shall be incremented when an acknowledgment to an A-MSDU is
not received when expected. This acknowledgment can be in an ACK or the
BlockAck frame."
::= { dot11CountersEntry 26 }
dot11ReceivedAMSDUCount OBJECT-TYPE
SYNTAX Counter32
MAX-ACCESS read-only
STATUS current
DESCRIPTION
"This is a status variable.
It is written by the MAC when an A-MSDU is received.
This counter shall be incremented for a received A-MSDU frame with the
station's MAC address in the address 1 field or an A-MSDU frame with a
group address in the address 1 field."
::= { dot11CountersEntry 27 }
dot11ReceivedOctetsInAMSDUCount OBJECT-TYPE
SYNTAX Counter64
MAX-ACCESS read-only
STATUS current
DESCRIPTION
"This is a status variable.
It is written by the MAC when an A-MSDU is received.
This counter shall be incremented by the number of octets in the framebody
of an A-MSDU frame when an A-MSDU frame is received."
::= { dot11CountersEntry 28 }
dot11TransmittedAMPDUCount OBJECT-TYPE
SYNTAX Counter32
MAX-ACCESS read-only
STATUS current
DESCRIPTION
"This is a status variable.
It is written by the MAC when an A-MPDU is transmitted.
This counter shall be incremented when an A-MPDU is transmitted."
::= { dot11CountersEntry 29 }
dot11TransmittedMPDUsInAMPDUCount OBJECT-TYPE
SYNTAX Counter32
MAX-ACCESS read-only
STATUS current
DESCRIPTION
"This is a status variable.
It is written by the MAC when an A-MPDU is transmitted.
This counter shall increment by the number of MPDUs in the A-MPDU when an
A-MPDU is transmitted."
::= { dot11CountersEntry 30 }
dot11TransmittedOctetsInAMPDUCount OBJECT-TYPE
SYNTAX Counter64
MAX-ACCESS read-only
STATUS current
DESCRIPTION
"This is a status variable.
It is written by the MAC when an A-MPDU is transmitted.
This counter shall be incremented by the number of octets in the A-MPDU
frame when an A-MPDU frame is transmitted."
::= { dot11CountersEntry 31 }
dot11AMPDUReceivedCount OBJECT-TYPE
SYNTAX Counter32
MAX-ACCESS read-only
STATUS current
DESCRIPTION
"This is a status variable.
It is written by the MAC when an A-MPDU is received.
This counter shall be incremented when the MAC receives an A-MPDU from the
PHY."
::= { dot11CountersEntry 32 }
dot11MPDUInReceivedAMPDUCount OBJECT-TYPE
SYNTAX Counter32
MAX-ACCESS read-only
STATUS current
DESCRIPTION
"This is a status variable.
It is written by the MAC when an A-MPDU is received.
This counter shall be incremented by the number of MPDUs received in the
A-MPDU when an A-MPDU is received."
::= { dot11CountersEntry 33 }
dot11ReceivedOctetsInAMPDUCount OBJECT-TYPE
SYNTAX Counter64
MAX-ACCESS read-only
STATUS current
DESCRIPTION
"This is a status variable.
It is written by the MAC when an A-MPDU is received.
This counter shall be incremented by the number of octets in the A-MPDU
frame when an A-MPDU frame is received."
::= { dot11CountersEntry 34 }
dot11AMPDUDelimiterCRCErrorCount OBJECT-TYPE
SYNTAX Counter32
MAX-ACCESS read-only
STATUS current
DESCRIPTION
"This is a status variable.
It is written by the MAC when the condition described below occurs.
This counter shall be incremented when an MPDU delimiter has a CRC error
when this is the first CRC error in the received A-MPDU or when the previous
delimiter has been decoded correctly."
::= { dot11CountersEntry 35 }
dot11ImplicitBARFailureCount OBJECT-TYPE
SYNTAX Counter32
MAX-ACCESS read-only
STATUS current
DESCRIPTION
"This is a status variable.
It is written by the MAC when the condition described below occurs.
This counter shall be incremented when the expected BlockAck is not
received in response to an Implicit BlockAckReq frame."
::= { dot11CountersEntry 36 }
dot11ExplicitBARFailureCount OBJECT-TYPE
SYNTAX Counter32
MAX-ACCESS read-only
STATUS current
DESCRIPTION
"This is a status variable.
It is written by the MAC when the condition described below occurs.
This counter shall be incremented when the expected BlockAck is not
received in response to an Explicit BlockAckReq."
::= { dot11CountersEntry 37 }
dot11ChannelWidthSwitchCount OBJECT-TYPE
SYNTAX Counter32
MAX-ACCESS read-only
STATUS current
DESCRIPTION
"This is a status variable.
It is written by the MAC when the bandwidth is switched.
This counter shall be increment when the bandwidth used is switched from
20 to 40 or vice-versa."
::= { dot11CountersEntry 38 }
dot11TwentyMHzFrameTransmittedCount OBJECT-TYPE
SYNTAX Counter32
MAX-ACCESS read-only
STATUS current
DESCRIPTION
"This is a status variable.
It is written by the MAC when a frame is transmitted only on the primary
channel.
This counter shall be incremented when a frame is transmitted only on the
primary channel."
::= { dot11CountersEntry 39 }
dot11FortyMHzFrameTransmittedCount OBJECT-TYPE
SYNTAX Counter32
MAX-ACCESS read-only
STATUS current
DESCRIPTION
"This is a status variable.
It is written by the MAC when a frame is transmitted on both control and
secondary channels.
This counter shall be incremented when a frame is transmitted on both control
and secondary channels."
::= { dot11CountersEntry 40 }
dot11TwentyMHzFrameReceivedCount OBJECT-TYPE
SYNTAX Counter32
MAX-ACCESS read-only
STATUS current
DESCRIPTION
"This is a status variable.
It is written by the MAC when a frame is received only on the primary
channel.
This counter shall be incremented when a frame is received only on the
primary channel."
::= { dot11CountersEntry 41 }
dot11FortyMHzFrameReceivedCount OBJECT-TYPE
SYNTAX Counter32
MAX-ACCESS read-only
STATUS current
DESCRIPTION
"This is a status variable.
It is written by the MAC when a frame is received on both the control and
secondary channels.
This counter shall be incremented when a frame is received on both the
control and secondary channels."
::= { dot11CountersEntry 42 }
dot11PSMPUTTGrantDuration OBJECT-TYPE
SYNTAX Counter32
MAX-ACCESS read-only
STATUS current
DESCRIPTION
"This is a status variable.
It is written by the MAC when a PSMP-UTT is granted.
This counter contains the cumulative duration of PSMP-UTT granted to the
STA, in units of 4 microseconds."
::= { dot11CountersEntry 43 }
dot11PSMPUTTUsedDuration OBJECT-TYPE
SYNTAX Counter32
MAX-ACCESS read-only
STATUS current
DESCRIPTION
"This is a status variable.
It is written by the MAC when a PSMP-UTT is used.
This counter contains the cumulative duration of transmission by the STA
during its allocated PSMP-UTT, in units of 4 microseconds"
::= { dot11CountersEntry 44 }
dot11GrantedRDGUsedCount OBJECT-TYPE
SYNTAX Counter32
MAX-ACCESS read-only
STATUS current
DESCRIPTION
"This is a status variable.
It is written by the MAC when an RDG is used.
This counter at the RD initiator shall be incremented when an allocated
RDG is used by the station, apart from transmitting a response frame such
as ACK or BlockAck frames."
::= { dot11CountersEntry 45 }
dot11GrantedRDGUnusedCount OBJECT-TYPE
SYNTAX Counter32
MAX-ACCESS read-only
STATUS current
DESCRIPTION
"This is a status variable.
It is written by the MAC when an RDG is not used.
This counter at the initiator shall be incremented when an allocated RDG
is not used by the station, apart from transmitting a response frame such
as ACK or BlockAck frames."
::= { dot11CountersEntry 46 }
dot11TransmittedFramesInGrantedRDGCount OBJECT-TYPE
SYNTAX Counter32
MAX-ACCESS read-only
STATUS current
DESCRIPTION
"This is a status variable.
It is written by the MAC when an RDG is used.
This counter at the initiator shall be incremented for every frame, other
than response frames such as ACK or BlockAck frames, transmitted by the
station during a granted RDG."
::= { dot11CountersEntry 47 }
dot11TransmittedOctetsInGrantedRDGCount OBJECT-TYPE
SYNTAX Counter64
MAX-ACCESS read-only
STATUS current
DESCRIPTION
"This is a status variable.
It is written by the MAC when an RDG is used.
This counter at the initiator shall be incremented by the number of octets
in the framebody of a frame, other than response frames such as ACK or
BlockAck frames, transmitted by the station during a granted RDG."
::= { dot11CountersEntry 48 }
dot11BeamformingFrameCount OBJECT-TYPE
SYNTAX Counter32
MAX-ACCESS read-only
STATUS current
DESCRIPTION
"This is a status variable.
It is written by the MAC when a frame with beamforming parameters is sent.
This counter shall be incremented when the transmitter sends a frame with
new/updated beamforming parameters."
::= { dot11CountersEntry 49 }
dot11DualCTSSuccessCount OBJECT-TYPE
SYNTAX Counter32
MAX-ACCESS read-only
STATUS current
DESCRIPTION
"This is a status variable.
It is written by the MAC when a dual CTS is sent.
This counter shall be incremented when AP sends a dual CTS in response to
a STA initiating TXOP in extended range."
::= { dot11CountersEntry 50 }
dot11DualCTSFailureCount OBJECT-TYPE
SYNTAX Counter32
MAX-ACCESS read-only
STATUS current
DESCRIPTION
"This is a status variable.
It is written by the MAC when a dual CTS is not sent.
This counter shall be incremented when AP fails to send a dual CTS in
response to a STA initiating TXOP in extended range."
::= { dot11CountersEntry 51 }
dot11STBCCTSSuccessCount OBJECT-TYPE
SYNTAX Counter32
MAX-ACCESS read-only
STATUS current
DESCRIPTION
"This is a status variable.
It is written by the MAC when no collision is detected.
This counter shall be incremented when AP does not detect a collision PIFS
after sending a CTS to self STBC frame in extended range."
::= { dot11CountersEntry 52 }
dot11STBCCTSFailureCount OBJECT-TYPE
SYNTAX Counter32
MAX-ACCESS read-only
STATUS current
DESCRIPTION
"This is a status variable.
It is written by the MAC when a collision is detected.
This counter shall be incremented when AP detects a collision PIFS after
sending a CTS to self STBC frame in extended range."
::= { dot11CountersEntry 53 }
dot11nonSTBCCTSSuccessCount OBJECT-TYPE
SYNTAX Counter32
MAX-ACCESS read-only
STATUS current
DESCRIPTION
"This is a status variable.
It is written by the MAC when no collision is detected.
This counter shall be incremented when AP does not detect a collision PIFS
after sending a CTS to self that is an non-STBC frame in extended range."
::= { dot11CountersEntry 54 }
dot11nonSTBCCTSFailureCount OBJECT-TYPE
SYNTAX Counter32
MAX-ACCESS read-only
STATUS current
DESCRIPTION
"This is a status variable.
It is written by the MAC when a collision is detected.
This counter shall be incremented when AP detects a collision PIFS after
sending a CTS to self that is an non-STBC frame in extended range."
::= { dot11CountersEntry 55 }
dot11RTSLSIGSuccessCount OBJECT-TYPE
SYNTAX Counter32
MAX-ACCESS read-only
STATUS current
DESCRIPTION
"This is a status variable.
It is written by the MAC when the condition described below occurs.
This counter shall be incremented when the duration/ID field is set
according to the rules of EPP in the received CTS following a transmission
of RTS in EPP mode."
::= { dot11CountersEntry 56 }
dot11RTSLSIGFailureCount OBJECT-TYPE
SYNTAX Counter32
MAX-ACCESS read-only
STATUS current
DESCRIPTION
"This is a status variable.
It is written by the MAC when the condition described below occurs.
This counter shall be incremented when the duration/ID field is not set
according to the rules of EPP in the received CTS following a transmission
of RTS in EPP mode."
::= { dot11CountersEntry 57 }
dot11PBACErrors OBJECT-TYPE
SYNTAX Counter32
MAX-ACCESS read-only
STATUS current
DESCRIPTION
"This is a status variable.
It is written by the MAC when the condition described below occurs.
This variable indicates the number of errors encountered in the PBAC procedures."
::= { dot11CountersEntry 58}
dot11DeniedAssociationCounterDueToBSSLoad OBJECT-TYPE
SYNTAX Counter32
MAX-ACCESS read-only
STATUS current
DESCRIPTION
"This is a status variable.
It is written by the SME when the condition described below occurs.
This counter, available at a WNM AP, shall increment when an association
or reassociation request is denied because the AP has insufficient bandwidth
to handle the additional STA."
::= { dot11CountersEntry 59}
-- **********************************************************************
-- * End of dot11Counters TABLE
-- **********************************************************************
-- **********************************************************************
-- * dot11GroupAddresses TABLE
-- **********************************************************************
dot11GroupAddressesTable OBJECT-TYPE
SYNTAX SEQUENCE OF Dot11GroupAddressesEntry
MAX-ACCESS not-accessible
STATUS current
DESCRIPTION
"A conceptual table containing a set of MAC addresses identifying the multicast-
group addresses for which this STA receives frames. The default
value of this attribute is null."
::= { dot11mac 3 }
dot11GroupAddressesEntry OBJECT-TYPE
SYNTAX Dot11GroupAddressesEntry
MAX-ACCESS not-accessible
STATUS current
DESCRIPTION
"An Entry (conceptual row) in the Group Addresses Table.
ifIndex - Each IEEE 802.11 interface is represented by an ifEntry. Interface
tables in this MIB module are indexed by ifIndex."
INDEX { ifIndex, dot11GroupAddressesIndex }
::= { dot11GroupAddressesTable 1 }
Dot11GroupAddressesEntry ::=
SEQUENCE {
dot11GroupAddressesIndex InterfaceIndex,
dot11Address MacAddress,
dot11GroupAddressesStatus RowStatus }
dot11GroupAddressesIndex OBJECT-TYPE
SYNTAX InterfaceIndex
MAX-ACCESS not-accessible
STATUS current
DESCRIPTION
"The auxiliary variable used to identify instances of the columnar objects
in the Group Addresses Table."
::= { dot11GroupAddressesEntry 1 }
dot11Address OBJECT-TYPE
SYNTAX MacAddress
MAX-ACCESS read-create
STATUS current
DESCRIPTION
"This is a control variable.
It is written by an external management entity.
Changes take effect as soon as practical in the implementation.
MAC address identifying multicast-group addresses from which this STA
receives frames."
::= { dot11GroupAddressesEntry 2 }
dot11GroupAddressesStatus OBJECT-TYPE
SYNTAX RowStatus
MAX-ACCESS read-create
STATUS current
DESCRIPTION
"The status column used for creating, modifying, and deleting instances of
the columnar objects in the Group Addresses Table."
DEFVAL { active }
::= { dot11GroupAddressesEntry 3 }
-- **********************************************************************
-- * End of dot11GroupAddresses TABLE
-- **********************************************************************
-- **********************************************************************
-- * SMT EDCA Config TABLE
-- **********************************************************************
dot11EDCATable OBJECT-TYPE
SYNTAX SEQUENCE OF Dot11EDCAEntry
MAX-ACCESS not-accessible
STATUS current
DESCRIPTION
"Conceptual table for EDCA default parameter values at a non-AP STA. This
table contains the four entries of the EDCA parameters corresponding to
four possible ACs. Index 1 corresponds to AC_BK, index 2 to AC_BE, index 3
to AC_VI, and index 4 to AC_VO."
REFERENCE
"IEEE 802.11-2012, 9.2.4.2"
::= { dot11mac 4 }
dot11EDCAEntry OBJECT-TYPE
SYNTAX Dot11EDCAEntry
MAX-ACCESS not-accessible
STATUS current
DESCRIPTION
"An Entry (conceptual row) in the EDCA Table.
ifIndex - Each IEEE 802.11 interface is represented by an ifEntry. Interface
tables in this MIB module are indexed by ifIndex."
INDEX { ifIndex, dot11EDCATableIndex }
::= { dot11EDCATable 1 }
Dot11EDCAEntry ::=
SEQUENCE {
dot11EDCATableIndex Unsigned32,
dot11EDCATableCWmin Unsigned32,
dot11EDCATableCWmax Unsigned32,
dot11EDCATableAIFSN Unsigned32,
dot11EDCATableTXOPLimit Unsigned32,
dot11EDCATableMSDULifetime Unsigned32,
dot11EDCATableMandatory TruthValue }
dot11EDCATableIndex OBJECT-TYPE
SYNTAX Unsigned32 (1..4)
MAX-ACCESS not-accessible
STATUS current
DESCRIPTION
"The auxiliary variable used to identify instances of the columnar objects
in the EDCA Table. The value of this variable is
1, if the value of the AC is AC_BK.
2, if the value of the AC is AC_BE.
3, if the value of the AC is AC_VI.
4, if the value of the AC is AC_VO."
::= { dot11EDCAEntry 1 }
dot11EDCATableCWmin OBJECT-TYPE
SYNTAX Unsigned32 (0..255)
MAX-ACCESS read-only
STATUS current
DESCRIPTION
"This is a control variable.
It is written by the MAC upon receiving an EDCA Parameter Set in a Beacon
frame.
Changes take effect as soon as practical in the implementation.
This attribute specifies the value of the minimum size of the window that
is used by a STA for a particular AC for generating a random number for
the backoff. The value of this attribute is such that it could always be
expressed in the form of 2**X - 1, where X is an integer. The default
value for this attribute is
aCWmin, if dot11EDCATableIndex is 1 or 2.
(aCWmin+1)/2 - 1, if dot11EDCATableIndex is 3.
(aCWmin+1)/4 - 1, if dot11EDCATableIndex is 4."
::= { dot11EDCAEntry 2 }
dot11EDCATableCWmax OBJECT-TYPE
SYNTAX Unsigned32 (0..65535)
MAX-ACCESS read-write
STATUS current
DESCRIPTION
"This is a control variable.
It is written by the MAC upon receiving an EDCA Parameter Set in a Beacon
frame.
Changes take effect as soon as practical in the implementation.
This attribute specifies the value of the maximum size of the window that
is used by a STA for a particular AC for generating a random number for
the backoff. The value of this attribute is such that it could always be
expressed in the form of 2**X - 1, where X is an integer. The default
value for this attribute is
aCWmax, if dot11EDCATableIndex is 1 or 2.
aCWmin, if dot11EDCATableIndex is 3.
(aCWmin+1)/2 - 1, if dot11EDCATableIndex is 4."
::= { dot11EDCAEntry 3 }
dot11EDCATableAIFSN OBJECT-TYPE
SYNTAX Unsigned32 (2..15)
MAX-ACCESS read-write
STATUS current
DESCRIPTION
"This is a control variable.
It is written by the MAC upon receiving an EDCA Parameter Set in a Beacon
frame.
Changes take effect as soon as practical in the implementation.
This attribute specifies the number of slots, after a SIFS duration, that
the STA, for a particular AC, senses the medium idle either before transmitting
or executing a backoff. The default value for this attribute is
7, if dot11EDCATableIndex is 1,
3, if dot11EDCATableIndex is 2
2, otherwise."
::= { dot11EDCAEntry 4 }
dot11EDCATableTXOPLimit OBJECT-TYPE
SYNTAX Unsigned32 (0..65535)
MAX-ACCESS read-write
STATUS current
DESCRIPTION
"This is a control variable.
It is written by the MAC upon receiving an EDCA Parameter Set in a Beacon
frame.
Changes take effect as soon as practical in the implementation.
This attribute specifies the maximum number of microseconds of an EDCA
TXOP for a given AC. The default value for this attribute is
1) 0 for all PHYs, if dot11EDCATableIndex is 1 or 2; this implies that
the sender can send one MSDU in an EDCA TXOP,
2) 3008 microseconds for Clause 18 and Clause 19 PHY and 6016 microseconds
for Clause 17 PHY, if dot11EDCATableIndex is 3,
3) 1504 microseconds for Clause 18 and Clause 19) PHY and 3264 microseconds
for Clause 17 PHY, if dot11EDCATableIndex is 4."
::= { dot11EDCAEntry 5 }
dot11EDCATableMSDULifetime OBJECT-TYPE
SYNTAX Unsigned32 (0..500)
MAX-ACCESS read-write
STATUS current
DESCRIPTION
"This is a control variable.
It is written by the MAC upon receiving an EDCA Parameter Set in a Beacon
frame.
Changes take effect as soon as practical in the implementation.
This attribute specifies (in TUs) the maximum duration an MSDU, for a
given AC, would be retained by the MAC before it is discarded."
DEFVAL { 500 }
::= { dot11EDCAEntry 6 }
dot11EDCATableMandatory OBJECT-TYPE
SYNTAX TruthValue
MAX-ACCESS read-write
STATUS current
DESCRIPTION
"This is a control variable.
It is written by the MAC upon receiving an EDCA Parameter Set in a Beacon
frame.
Changes take effect as soon as practical in the implementation.
This attribute, when true, indicates that admission control is mandatory
for the given AC. When false, this attribute indicates that the admission
control is not mandatory for the given AC."
DEFVAL { false }
::= { dot11EDCAEntry 7 }
-- **********************************************************************
-- * End of SMT EDCA Config TABLE
-- **********************************************************************
-- **********************************************************************
-- * SMT AP EDCA Config TABLE
-- **********************************************************************
dot11QAPEDCATable OBJECT-TYPE
SYNTAX SEQUENCE OF Dot11QAPEDCAEntry
MAX-ACCESS not-accessible
STATUS current
DESCRIPTION
"Conceptual table for EDCA default parameter values at the AP. This table
contains the four entries of the EDCA parameters corresponding to four
possible ACs. Index 1 corresponds to AC_BK, index 2 to AC_BE, index 3 to
AC_VI, and index 4 to AC_VO."
REFERENCE
"IEEE 802.11-2012, 9.19.2"
::= { dot11mac 5 }
dot11QAPEDCAEntry OBJECT-TYPE
SYNTAX Dot11QAPEDCAEntry
MAX-ACCESS not-accessible
STATUS current
DESCRIPTION
"An Entry (conceptual row) in the EDCA Table.
ifIndex - Each IEEE 802.11 interface is represented by an ifEntry. Interface
tables in this MIB module are indexed by ifIndex."
INDEX { ifIndex, dot11QAPEDCATableIndex }
::= { dot11QAPEDCATable 1 }
Dot11QAPEDCAEntry ::=
SEQUENCE {
dot11QAPEDCATableIndex Unsigned32,
dot11QAPEDCATableCWmin Unsigned32,
dot11QAPEDCATableCWmax Unsigned32,
dot11QAPEDCATableAIFSN Unsigned32,
dot11QAPEDCATableTXOPLimit Unsigned32,
dot11QAPEDCATableMSDULifetime Unsigned32,
dot11QAPEDCATableMandatory TruthValue }
dot11QAPEDCATableIndex OBJECT-TYPE
SYNTAX Unsigned32 (1..4)
MAX-ACCESS not-accessible
STATUS current
DESCRIPTION
"The auxiliary variable used to identify instances of the columnar objects
in the EDCA Table. The value of this variable is
1, if the value of the AC is AC_BK.
2, if the value of the AC is AC_BE.
3, if the value of the AC is AC_VI.
4, if the value of the AC is AC_VO."
::= { dot11QAPEDCAEntry 1 }
dot11QAPEDCATableCWmin OBJECT-TYPE
SYNTAX Unsigned32 (0..255)
MAX-ACCESS read-write
STATUS current
DESCRIPTION
"This is a control variable.
It is written by an external management entity.
Changes take effect as soon as practical in the implementation.
This attribute specifies the value of the minimum size of the window that
is used by an AP for a particular AC for generating a random number for
the backoff. The value of this attribute is such that it could always be
expressed in the form of 2**X - 1, where X is an integer. The default
value for this attribute is
aCWmin, if dot11QAPEDCATableIndex is 1 or 2.
(aCWmin+1)/2 - 1, if dot11QAPEDCATableIndex is 3.
(aCWmin+1)/4 - 1, if dot11QAPEDCATableIndex is 4."
::= { dot11QAPEDCAEntry 2 }
dot11QAPEDCATableCWmax OBJECT-TYPE
SYNTAX Unsigned32 (0..65535)
MAX-ACCESS read-write
STATUS current
DESCRIPTION
"This is a control variable.
It is written by an external management entity.
Changes take effect as soon as practical in the implementation.
This attribute specifies the value of the maximum size of the window that
is used by an AP for a particular AC for generating a random number for
the backoff. The value of this attribute is such that it could always be
expressed in the form of 2**X - 1, where X is an integer. The default
value for this attribute is
aCWmax, if dot11QAPEDCATableIndex is 1.
4*(aCWmin+1) - 1, if dot11QAPEDCATableIndex is 2.
aCWmin, if dot11QAPEDCATableIndex is 3.
(aCWmin+1)/2 - 1, if dot11QAPEDCATableIndex is 4."
::= { dot11QAPEDCAEntry 3 }
dot11QAPEDCATableAIFSN OBJECT-TYPE
SYNTAX Unsigned32 (1..15)
MAX-ACCESS read-write
STATUS current
DESCRIPTION
"This is a control variable.
It is written by an external management entity.
Changes take effect as soon as practical in the implementation.
This attribute specifies the number of slots, after a SIFS duration, that
the AP, for a particular AC, senses the medium idle either before transmitting 
or executing a backoff. The default value for this attribute is
7, if dot11QAPEDCATableIndex is 1,
3, if dot11QAPEDCATableIndex is 2
1, otherwise."
::= { dot11QAPEDCAEntry 4 }
dot11QAPEDCATableTXOPLimit OBJECT-TYPE
SYNTAX Unsigned32 (0..65535)
MAX-ACCESS read-write
STATUS current
DESCRIPTION
"This is a control variable.
It is written by an external management entity.
Changes take effect as soon as practical in the implementation.
This attribute specifies the maximum number of microseconds of an EDCA
TXOP for a given AC at the AP. The default value for this attribute is
1) 0 for all PHYs, if dot11QAPEDCATableIndex is 1 or 2; this implies that
the sender can send one MSDU in an EDCA TXOP,
2) 3008 microseconds for Clause 18 and Clause 19 PHY and 6016 microseconds
for Clause 17 PHY, if dot11QAPEDCATableIndex is 3,
3) 1504 microseconds for Clause 18 and Clause 19 PHY and 3264 microseconds
for Clause 17 PHY, if dot11QAPEDCATableIndex is 4."
::= { dot11QAPEDCAEntry 5 }
dot11QAPEDCATableMSDULifetime OBJECT-TYPE
SYNTAX Unsigned32 (0..500)
MAX-ACCESS read-write
STATUS current
DESCRIPTION
"This is a control variable.
It is written by an external management entity.
Changes take effect as soon as practical in the implementation.
This attribute specifies (in TUs) the maximum duration an MSDU, for a
given AC, would be retained by the MAC at the AP before it is discarded."
DEFVAL { 500 }
::= { dot11QAPEDCAEntry 6 }
dot11QAPEDCATableMandatory OBJECT-TYPE
SYNTAX TruthValue
MAX-ACCESS read-write
STATUS current
DESCRIPTION
"This is a control variable.
It is written by an external management entity.
Changes take effect as soon as practical in the implementation.
This attribute, when true, indicates that admission control is mandatory
for the given AC. When false, this attribute indicates that the admission
control is not mandatory for the given AC. The default value for this
parameter is false."
::= { dot11QAPEDCAEntry 7 }
-- **********************************************************************
-- * End of SMT AP EDCA Config TABLE
-- **********************************************************************
-- **********************************************************************
-- * dot11QosCounters TABLE
-- **********************************************************************
dot11QosCountersTable OBJECT-TYPE
SYNTAX SEQUENCE OF Dot11QosCountersEntry
MAX-ACCESS not-accessible
STATUS current
DESCRIPTION
"Group containing attributes that are MAC counters implemented as a table
to allow for multiple instantiations on an agent."
::= { dot11mac 6 }
dot11QosCountersEntry OBJECT-TYPE
SYNTAX Dot11QosCountersEntry
MAX-ACCESS not-accessible
STATUS current
DESCRIPTION
"An Entry (conceptual row) in the EDCA Table.
ifIndex - Each IEEE 802.11 interface is represented by an ifEntry. Interface
tables in this MIB module are indexed by ifIndex."
INDEX { ifIndex, dot11QosCountersIndex }
::= { dot11QosCountersTable 1 }
Dot11QosCountersEntry ::=
SEQUENCE {
dot11QosCountersIndex Unsigned32,
dot11QosTransmittedFragmentCount Counter32,
dot11QosFailedCount Counter32,
dot11QosRetryCount Counter32,
dot11QosMultipleRetryCount Counter32,
dot11QosFrameDuplicateCount Counter32,
dot11QosRTSSuccessCount Counter32,
dot11QosRTSFailureCount Counter32,
dot11QosACKFailureCount Counter32,
dot11QosReceivedFragmentCount Counter32,
dot11QosTransmittedFrameCount Counter32,
dot11QosDiscardedFrameCount Counter32,
dot11QosMPDUsReceivedCount Counter32,
dot11QosRetriesReceivedCount Counter32 }
dot11QosCountersIndex OBJECT-TYPE
SYNTAX Unsigned32 (1..16)
MAX-ACCESS not-accessible
STATUS current
DESCRIPTION
"The auxiliary variable used to identify instances of the columnar objects
in the QoSCounter Table. The value of this variable is equal to TID + 1."
::= { dot11QosCountersEntry 1 }
dot11QosTransmittedFragmentCount OBJECT-TYPE
SYNTAX Counter32
MAX-ACCESS read-only
STATUS current
DESCRIPTION
"This is a status variable.
It is written by the MAC when a QoS fragment is transmitted.
This counter is incremented for an acknowledged MPDU, for a particular UP,
with an individual address in the address 1 field or an MPDU with a group
address in the address 1 field, either belonging to a particular TID. This
counter has relevance only for TIDs between 0 and 7."
::= { dot11QosCountersEntry 2 }
dot11QosFailedCount OBJECT-TYPE
SYNTAX Counter32
MAX-ACCESS read-only
STATUS current
DESCRIPTION
"This is a status variable.
It is written by the MAC when the condition described below occurs.
This counter increments when an MSDU, for a particular UP, is not transmitted
successfully due to the number of transmit attempts exceeding
either the dot11ShortRetryLimit or dot11LongRetryLimit. This counter has
relevance only for TIDs between 0 and 7."
::= { dot11QosCountersEntry 3 }
dot11QosRetryCount OBJECT-TYPE
SYNTAX Counter32
MAX-ACCESS read-only
STATUS current
DESCRIPTION
"This is a status variable.
It is written by the MAC when the condition described below occurs.
This counter increments when an MSDU, of a particular UP, is successfully
transmitted after one or more retransmissions. This counter has relevance
only for TIDs between 0 and 7."
::= { dot11QosCountersEntry 4 }
dot11QosMultipleRetryCount OBJECT-TYPE
SYNTAX Counter32
MAX-ACCESS read-only
STATUS current
DESCRIPTION
"This is a status variable.
It is written by the MAC when the condition described below occurs.
This counter increments when an MSDU, of a particular UP, is successfully
transmitted after more than one retransmissions. This counter has relevance
only for TIDs between 0 and 7."
::= { dot11QosCountersEntry 5 }
dot11QosFrameDuplicateCount OBJECT-TYPE
SYNTAX Counter32
MAX-ACCESS read-only
STATUS current
DESCRIPTION
"This is a status variable.
It is written by the MAC when the condition described below occurs.
This counter increments when a frame, of a particular UP, is received that
the Sequence Control field indicates is a duplicate. This counter has relevance
only for TIDs between 0 and 7."
::= { dot11QosCountersEntry 6 }
dot11QosRTSSuccessCount OBJECT-TYPE
SYNTAX Counter32
MAX-ACCESS read-only
STATUS current
DESCRIPTION
"This is a status variable.
It is written by the MAC when a CTS is received in response to an RTS.
This counter increments when a CTS is received in response to an RTS that
has been sent for the transmission of an MPDU of a particular UP. This
counter has relevance only for TIDs between 0 and 7."
::= { dot11QosCountersEntry 7 }
dot11QosRTSFailureCount OBJECT-TYPE
SYNTAX Counter32
MAX-ACCESS read-only
STATUS current
DESCRIPTION
"This is a status variable.
It is written by the MAC when the condition described below occurs.
This counter increments when a CTS is not received in response to an RTS
that has been sent for the transmission of an MPDU of a particular UP.
This counter has relevance only for TIDs between 0 and 7."
::= { dot11QosCountersEntry 8 }
dot11QosACKFailureCount OBJECT-TYPE
SYNTAX Counter32
MAX-ACCESS read-only
STATUS current
DESCRIPTION
"This is a status variable.
It is written by the MAC when the condition described below occurs.
This counter increments when an ACK is not received in response to an MPDU
of a particular UP. This counter has relevance only for TIDs between 0 and
7."
::= { dot11QosCountersEntry 9 }
dot11QosReceivedFragmentCount OBJECT-TYPE
SYNTAX Counter32
MAX-ACCESS read-only
STATUS current
DESCRIPTION
"This is a status variable.
It is written by the MAC when a QoS fragment is received.
This counter is incremented for each successfully received MPDU of type
Data of a particular UP. This counter has relevance only for TIDs between
0 and 7."
::= { dot11QosCountersEntry 10 }
dot11QosTransmittedFrameCount OBJECT-TYPE
SYNTAX Counter32
MAX-ACCESS read-only
STATUS current
DESCRIPTION
"This is a status variable.
It is written by the MAC when a QoS frame is transmitted.
This counter increments for each successfully transmitted MSDU of a particular
UP. This counter has relevance only for TIDs between 0 and 7."
::= { dot11QosCountersEntry 11 }
dot11QosDiscardedFrameCount OBJECT-TYPE
SYNTAX Counter32
MAX-ACCESS read-only
STATUS current
DESCRIPTION
"This is a status variable.
It is written by the MAC when the condition described below occurs.
This counter increments for each Discarded MSDU of a particular UP. This
counter has relevance only for TIDs between 0 and 7."
::= { dot11QosCountersEntry 12 }
dot11QosMPDUsReceivedCount OBJECT-TYPE
SYNTAX Counter32
MAX-ACCESS read-only
STATUS current
DESCRIPTION
"This is a status variable.
It is written by the MAC when a QoS MPDU is received.
This counter increments for each received MPDU of a particular TID."
::= { dot11QosCountersEntry 13 }
dot11QosRetriesReceivedCount OBJECT-TYPE
SYNTAX Counter32
MAX-ACCESS read-only
STATUS current
DESCRIPTION
"This is a status variable.
It is written by the MAC when the condition described below occurs.
This counter increments for each received MPDU of a particular TID with
the retry bit equal to 1."
::= { dot11QosCountersEntry 14 }
-- **********************************************************************
-- * End of dot11QosCounters TABLE
-- **********************************************************************
-- **********************************************************************
-- * Resource Type Attribute Templates
-- **********************************************************************
dot11ResourceTypeIDName OBJECT-TYPE
SYNTAX DisplayString (SIZE(4))
MAX-ACCESS read-only
STATUS current
DESCRIPTION
"Contains the name of the Resource Type ID managed object. The attribute
is read-only and always contains the value RTID. This attribute value is
not used as a naming attribute for any other managed object class."
REFERENCE "IEEE Std 802.1F-1993, A.7"
DEFVAL { "RTID" }
::= { dot11resAttribute 1 }
-- **********************************************************************
-- * dot11ResourceInfo TABLE
-- **********************************************************************
dot11ResourceInfoTable OBJECT-TYPE
SYNTAX SEQUENCE OF Dot11ResourceInfoEntry
MAX-ACCESS not-accessible
STATUS current
DESCRIPTION
"Provides a means of indicating, in data readable from a managed object,
information that identifies the source of the implementation."
REFERENCE "IEEE Std 802.1F-1993, A.7. Note that this standard has been withdrawn."
::= { dot11resAttribute 2 }
dot11ResourceInfoEntry OBJECT-TYPE
SYNTAX Dot11ResourceInfoEntry
MAX-ACCESS not-accessible
STATUS current
DESCRIPTION
"An entry in the dot11ResourceInfo Table.
ifIndex - Each IEEE 802.11 interface is represented by an ifEntry. Interface
tables in this MIB module are indexed by ifIndex."
INDEX { ifIndex }
::= { dot11ResourceInfoTable 1 }
Dot11ResourceInfoEntry ::=
SEQUENCE {
dot11manufacturerOUI OCTET STRING,
dot11manufacturerName DisplayString,
dot11manufacturerProductName DisplayString,
dot11manufacturerProductVersion DisplayString }
dot11manufacturerOUI OBJECT-TYPE
SYNTAX OCTET STRING (SIZE(3))
MAX-ACCESS read-only
STATUS current
DESCRIPTION
"This is a capability variable.
Its value is determined by device capabilities.
Takes the value of an organizationally unique identifier."
::= { dot11ResourceInfoEntry 1 }
dot11manufacturerName OBJECT-TYPE
SYNTAX DisplayString (SIZE(0..128))
MAX-ACCESS read-only
STATUS current
DESCRIPTION
"This is a capability variable.
Its value is determined by device capabilities.
A printable string used to identify the manufacturer of the resource. Maximum
string length is 128 octets."
::= { dot11ResourceInfoEntry 2 }
dot11manufacturerProductName OBJECT-TYPE
SYNTAX DisplayString (SIZE(0..128))
MAX-ACCESS read-only
STATUS current
DESCRIPTION
"This is a capability variable.
Its value is determined by device capabilities.
A printable string used to identify the manufacturer's product name of the
resource. Maximum string length is 128 octets."
::= { dot11ResourceInfoEntry 3 }
dot11manufacturerProductVersion OBJECT-TYPE
SYNTAX DisplayString (SIZE(0..128))
MAX-ACCESS read-only
STATUS current
DESCRIPTION
"This is a capability variable.
Its value is determined by device capabilities.
Printable string used to identify the manufacturer's product version of
the resource. Maximum string length is 128 octets."
::= { dot11ResourceInfoEntry 4 }
-- **********************************************************************
-- * End of dot11ResourceInfo TABLE
-- **********************************************************************
-- **********************************************************************
-- * PHY Attribute Templates
-- **********************************************************************
-- **********************************************************************
-- * dot11PhyOperation TABLE
-- **********************************************************************
dot11PhyOperationTable OBJECT-TYPE
SYNTAX SEQUENCE OF Dot11PhyOperationEntry
MAX-ACCESS not-accessible
STATUS current
DESCRIPTION
"PHY level attributes concerned with operation. Implemented as a table
indexed on ifIndex to allow for multiple instantiations on an Agent."
::= { dot11phy 1 }
dot11PhyOperationEntry OBJECT-TYPE
SYNTAX Dot11PhyOperationEntry
MAX-ACCESS not-accessible
STATUS current
DESCRIPTION
"An entry in the dot11PhyOperation Table.
ifIndex - Each IEEE 802.11 interface is represented by an ifEntry. Interface
tables in this MIB module are indexed by ifIndex."
INDEX { ifIndex }
::= { dot11PhyOperationTable 1 }
Dot11PhyOperationEntry ::=
SEQUENCE {
dot11PHYType INTEGER,
dot11CurrentRegDomain Unsigned32,
dot11TempType INTEGER }
dot11PHYType OBJECT-TYPE
SYNTAX INTEGER {
fhss(1),
dsss(2),
irbaseband(3),
ofdm(4),
hrdsss(5),
erp(6),
ht(7) }
MAX-ACCESS read-only
STATUS current
DESCRIPTION
"This is a status variable.
It is written by the PHY.
This is an 8-bit integer value that identifies the PHY type supported by
the attached PLCP and PMD. Currently defined values and their corresponding
PHY types are:
FHSS 2.4 GHz = 01, DSSS 2.4 GHz = 02, IR Baseband = 03,
OFDM = 04, HRDSSS = 05, ERP = 06, HT = 07"
::= { dot11PhyOperationEntry 1 }
dot11CurrentRegDomain OBJECT-TYPE
SYNTAX Unsigned32
MAX-ACCESS read-only
STATUS current
DESCRIPTION
"This is a control variable.
It is written by the SME when the device is initialized.
The current regulatory domain this instance of the PMD is supporting. This
object corresponds to one of the RegDomains listed in
dot11RegDomainsSupported."
::= { dot11PhyOperationEntry 2 }
dot11TempType OBJECT-TYPE
SYNTAX INTEGER { tempType1(1), tempType2(2) }
MAX-ACCESS read-only
STATUS deprecated
DESCRIPTION
"The use of dot11TempType is deprecated, because references to this variable
have been removed from the normative text of IEEE Std 802.11-2012,
and this entity may be removed in a later revision of the standard.
This is a status variable.
It is written by the PHY.
There are different operating temperature requirements dependent on the
anticipated environmental conditions. This attribute describes the current
PHY's operating temperature range capability. Currently defined values and
their corresponding temperature ranges are:
Type 1 = X'01'-Commercial range of 0 to 40 degrees C,
Type 2 = X'02'-Industrial range of -30 to 70 degrees C."
::= { dot11PhyOperationEntry 3 }
-- **********************************************************************
-- * End of dot11PhyOperation TABLE
-- **********************************************************************
-- **********************************************************************
-- * dot11PhyAntenna TABLE
-- **********************************************************************
dot11PhyAntennaTable OBJECT-TYPE
SYNTAX SEQUENCE OF Dot11PhyAntennaEntry
MAX-ACCESS not-accessible
STATUS current
DESCRIPTION
"Group of attributes for PhyAntenna. Implemented as a table indexed on
ifIndex to allow for multiple instances on an agent."
::= { dot11phy 2}
dot11PhyAntennaEntry OBJECT-TYPE
SYNTAX Dot11PhyAntennaEntry
MAX-ACCESS not-accessible
STATUS current
DESCRIPTION
"An entry in the dot11PhyAntenna Table.
ifIndex - Each IEEE 802.11 interface is represented by an ifEntry. Interface
tables in this MIB module are indexed by ifIndex."
INDEX { ifIndex }
::= { dot11PhyAntennaTable 1 }
Dot11PhyAntennaEntry ::=
SEQUENCE {
dot11CurrentTxAntenna Unsigned32,
dot11DiversitySupportImplemented INTEGER,
dot11CurrentRxAntenna Unsigned32,
dot11AntennaSelectionOptionImplemented TruthValue,
dot11TransmitExplicitCSIFeedbackASOptionImplemented TruthValue,
dot11TransmitIndicesFeedbackASOptionImplemented TruthValue,
dot11ExplicitCSIFeedbackASOptionImplemented TruthValue,
dot11TransmitIndicesComputationASOptionImplemented TruthValue,
dot11ReceiveAntennaSelectionOptionImplemented TruthValue,
dot11TransmitSoundingPPDUOptionImplemented TruthValue,
dot11NumberOfActiveRxAntennas Unsigned32 }
dot11CurrentTxAntenna OBJECT-TYPE
SYNTAX Unsigned32 (1..255)
MAX-ACCESS read-write
STATUS current
DESCRIPTION
"This is a control variable.
It is written by an external management entity.
Changes take effect as soon as practical in the implementation.
The current antenna being used to transmit. This value is one of the values
appearing in dot11TxAntennaImplemented. This may be used by a management
agent to control which antenna is used for transmission. "
::= { dot11PhyAntennaEntry 1 }
dot11DiversitySupportImplemented OBJECT-TYPE
SYNTAX INTEGER { fixedlist(1), notsupported(2), dynamic(3) }
MAX-ACCESS read-only
STATUS current
DESCRIPTION
"This is a capability variable.
Its value is determined by device capabilities.
This implementation's support for diversity, encoded as:
X'01'-diversity is available and is performed over the fixed list of
antennas defined in dot11DiversitySelectionRxImplemented.
X'02'-diversity is not supported.
X'03'-diversity is supported and control of diversity is also available,
in which case the attribute dot11DiversitySelectionRxImplemented can be
dynamically modified by the LME."
::= { dot11PhyAntennaEntry 2 }
dot11CurrentRxAntenna OBJECT-TYPE
SYNTAX Unsigned32 (1..255)
MAX-ACCESS read-only
STATUS current
DESCRIPTION
"This is a status variable.
It is written by the PHY.
The current antenna being used to receive, if the dot11 DiversitySupport
indicates that diversity is not supported. The selected antenna is one of
the antennae marked for receive in the dot11AntennasListTable."
::= { dot11PhyAntennaEntry 3 }
dot11AntennaSelectionOptionImplemented OBJECT-TYPE
SYNTAX TruthValue
MAX-ACCESS read-only
STATUS current
DESCRIPTION
"This is a capability variable.
Its value is determined by device capabilities.
This attribute, when true, indicates that ASEL is supported by the station
implementation."
DEFVAL { false }
::= { dot11PhyAntennaEntry 4 }
dot11TransmitExplicitCSIFeedbackASOptionImplemented OBJECT-TYPE
SYNTAX TruthValue
MAX-ACCESS read-only
STATUS current
DESCRIPTION
"This is a capability variable.
Its value is determined by device capabilities.
This attribute, when true, indicates that the transmit ASEL based on
explicit CSI feedback is supported by the station implementation."
DEFVAL { false }
::= { dot11PhyAntennaEntry 5 }
dot11TransmitIndicesFeedbackASOptionImplemented OBJECT-TYPE
SYNTAX TruthValue
MAX-ACCESS read-only
STATUS current
DESCRIPTION
"This is a capability variable.
Its value is determined by device capabilities.
This attribute, when true, indicates that the transmit ASEL based on
antenna indices feedback is supported by the station implementation."
DEFVAL { false }
::= { dot11PhyAntennaEntry 6 }
dot11ExplicitCSIFeedbackASOptionImplemented OBJECT-TYPE
SYNTAX TruthValue
MAX-ACCESS read-only
STATUS current
DESCRIPTION
"This is a capability variable.
Its value is determined by device capabilities.
This attribute, when true, indicates that the computation of CSI and feedback
the results to support the peer to do ASEL is supported by the station
implementation."
DEFVAL { false }
::= { dot11PhyAntennaEntry 7 }
dot11TransmitIndicesComputationASOptionImplemented OBJECT-TYPE
SYNTAX TruthValue
MAX-ACCESS read-only
STATUS current
DESCRIPTION
"This is a capability variable.
Its value is determined by device capabilities.
This attribute, when true, indicates that the transmit ASEL based on
antenna indices selection computation and feedback the results to support
the peer to do ASEL is supported by the station implementation."
DEFVAL { false }
::= { dot11PhyAntennaEntry 8 }
dot11ReceiveAntennaSelectionOptionImplemented OBJECT-TYPE
SYNTAX TruthValue
MAX-ACCESS read-only
STATUS current
DESCRIPTION
"This is a capability variable.
Its value is determined by device capabilities.
This attribute, when true, indicates that the receive ASEL is supported by
the station implementation."
DEFVAL { false }
::= { dot11PhyAntennaEntry 9 }
dot11TransmitSoundingPPDUOptionImplemented OBJECT-TYPE
SYNTAX TruthValue
MAX-ACCESS read-only
STATUS current
DESCRIPTION
"This is a capability variable.
Its value is determined by device capabilities.
This attribute, when true, indicates that the transmission of sounding
PPDUs is supported by the station implementation."
DEFVAL { false }
::= { dot11PhyAntennaEntry 10 }
dot11NumberOfActiveRxAntennas OBJECT-TYPE
SYNTAX Unsigned32 (1..4)
MAX-ACCESS read-only
STATUS current
DESCRIPTION
"This is a status variable.
It is written by the PHY.
This attribute indicates the number of current active antennas being used
to receive."
::= { dot11PhyAntennaEntry 11 }
-- **********************************************************************
-- * End of dot11PhyAntenna TABLE
-- **********************************************************************
-- **********************************************************************
-- * dot11PhyTxPower TABLE
-- **********************************************************************
dot11PhyTxPowerTable OBJECT-TYPE
SYNTAX SEQUENCE OF Dot11PhyTxPowerEntry
MAX-ACCESS not-accessible
STATUS current
DESCRIPTION
"Group of attributes for dot11PhyTxPowerTable. Implemented as a table
indexed on STA ID to allow for multiple instances on an Agent."
::= { dot11phy 3}
dot11PhyTxPowerEntry OBJECT-TYPE
SYNTAX Dot11PhyTxPowerEntry
MAX-ACCESS not-accessible
STATUS current
DESCRIPTION
"An entry in the dot11PhyTxPower Table.
ifIndex - Each IEEE 802.11 interface is represented by an ifEntry. Interface
tables in this MIB module are indexed by ifIndex."
INDEX { ifIndex }
::= { dot11PhyTxPowerTable 1 }
Dot11PhyTxPowerEntry ::=
SEQUENCE {
dot11NumberSupportedPowerLevelsImplemented Unsigned32,
dot11TxPowerLevel1 Unsigned32,
dot11TxPowerLevel2 Unsigned32,
dot11TxPowerLevel3 Unsigned32,
dot11TxPowerLevel4 Unsigned32,
dot11TxPowerLevel5 Unsigned32,
dot11TxPowerLevel6 Unsigned32,
dot11TxPowerLevel7 Unsigned32,
dot11TxPowerLevel8 Unsigned32,
dot11CurrentTxPowerLevel Unsigned32 }
dot11NumberSupportedPowerLevelsImplemented OBJECT-TYPE
SYNTAX Unsigned32 (1..8)
MAX-ACCESS read-only
STATUS current
DESCRIPTION
"This is a capability variable.
Its value is determined by device capabilities.
The number of power levels supported by the PMD. This attribute can have a
value of 1 to 8."
::= { dot11PhyTxPowerEntry 1 }
dot11TxPowerLevel1 OBJECT-TYPE
SYNTAX Unsigned32 (0..10000)
MAX-ACCESS read-only
STATUS current
DESCRIPTION
"This is a capability variable.
Its value is determined by device capabilities.
The transmit output power for LEVEL1 in mW. This is also the default power
level."
::= { dot11PhyTxPowerEntry 2 }
dot11TxPowerLevel2 OBJECT-TYPE
SYNTAX Unsigned32 (0..10000)
MAX-ACCESS read-only
STATUS current
DESCRIPTION
"This is a capability variable.
Its value is determined by device capabilities.
The transmit output power for LEVEL2 in mW."
::= { dot11PhyTxPowerEntry 3 }
dot11TxPowerLevel3 OBJECT-TYPE
SYNTAX Unsigned32 (0..10000)
MAX-ACCESS read-only
STATUS current
DESCRIPTION
"This is a capability variable.
Its value is determined by device capabilities.
The transmit output power for LEVEL3 in mW."
::= { dot11PhyTxPowerEntry 4 }
dot11TxPowerLevel4 OBJECT-TYPE
SYNTAX Unsigned32 (0..10000)
MAX-ACCESS read-only
STATUS current
DESCRIPTION
"This is a capability variable.
Its value is determined by device capabilities.
The transmit output power for LEVEL4 in mW."
::= { dot11PhyTxPowerEntry 5 }
dot11TxPowerLevel5 OBJECT-TYPE
SYNTAX Unsigned32 (0..10000)
MAX-ACCESS read-only
STATUS current
DESCRIPTION
"This is a capability variable.
Its value is determined by device capabilities.
The transmit output power for LEVEL5 in mW."
::= { dot11PhyTxPowerEntry 6 }
dot11TxPowerLevel6 OBJECT-TYPE
SYNTAX Unsigned32 (0..10000)
MAX-ACCESS read-only
STATUS current
DESCRIPTION
"This is a capability variable.
Its value is determined by device capabilities.
The transmit output power for LEVEL6 in mW."
::= { dot11PhyTxPowerEntry 7 }
dot11TxPowerLevel7 OBJECT-TYPE
SYNTAX Unsigned32 (0..10000)
MAX-ACCESS read-only
STATUS current
DESCRIPTION
"This is a capability variable.
Its value is determined by device capabilities.
The transmit output power for LEVEL7 in mW."
::= { dot11PhyTxPowerEntry 8 }
dot11TxPowerLevel8 OBJECT-TYPE
SYNTAX Unsigned32 (0..10000)
MAX-ACCESS read-only
STATUS current
DESCRIPTION
"This is a capability variable.
Its value is determined by device capabilities.
The transmit output power for LEVEL8 in mW."
::= { dot11PhyTxPowerEntry 9 }
dot11CurrentTxPowerLevel OBJECT-TYPE
SYNTAX Unsigned32 (1..8)
MAX-ACCESS read-only
STATUS current
DESCRIPTION
"This is a status variable.
It is written by the PHY.
The TxPowerLevel N currently being used to transmit data. Some PHYs also
use this value to determine the receiver sensitivity requirements for
CCA."
::= { dot11PhyTxPowerEntry 10 }
-- **********************************************************************
-- * End of dot11PhyTxPower TABLE
-- **********************************************************************
-- **********************************************************************
-- * dot11PhyFHSS TABLE
-- **********************************************************************
dot11PhyFHSSTable OBJECT-TYPE
SYNTAX SEQUENCE OF Dot11PhyFHSSEntry
MAX-ACCESS not-accessible
STATUS current
DESCRIPTION
"Group of attributes for dot11PhyFHSSTable. Implemented as a table indexed
on STA ID to allow for multiple instances on an Agent."
::= { dot11phy 4 }
dot11PhyFHSSEntry OBJECT-TYPE
SYNTAX Dot11PhyFHSSEntry
MAX-ACCESS not-accessible
STATUS current
DESCRIPTION
"An entry in the dot11PhyFHSS Table.
ifIndex - Each IEEE 802.11 interface is represented by an ifEntry. Interface
tables in this MIB module are indexed by ifIndex."
INDEX { ifIndex }
::= { dot11PhyFHSSTable 1 }
Dot11PhyFHSSEntry ::=
SEQUENCE {
dot11HopTime Unsigned32,
dot11CurrentChannelNumber Unsigned32,
dot11MaxDwellTime Unsigned32,
dot11CurrentDwellTime Unsigned32,
dot11CurrentSet Unsigned32,
dot11CurrentPattern Unsigned32,
dot11CurrentIndex Unsigned32,
dot11EHCCPrimeRadix Unsigned32,
dot11EHCCNumberofChannelsFamilyIndex Unsigned32,
dot11EHCCCapabilityImplemented TruthValue,
dot11EHCCCapabilityActivated TruthValue,
dot11HopAlgorithmAdopted INTEGER,
dot11RandomTableFlag TruthValue,
dot11NumberofHoppingSets Unsigned32,
dot11HopModulus Unsigned32,
dot11HopOffset Unsigned32 }
dot11HopTime OBJECT-TYPE
SYNTAX Unsigned32 (224)
MAX-ACCESS read-only
STATUS current
DESCRIPTION
"This is a capability variable.
Its value is determined by device capabilities.
The time in microseconds for the PMD to change from channel 2 to channel
80."
::= { dot11PhyFHSSEntry 1 }
dot11CurrentChannelNumber OBJECT-TYPE
SYNTAX Unsigned32 (0..200)
MAX-ACCESS read-only
STATUS current
DESCRIPTION
"This is a status variable.
It is written by the PHY.
The current channel number of the frequency output by the RF synthesizer."
::= { dot11PhyFHSSEntry 2 }
dot11MaxDwellTime OBJECT-TYPE
SYNTAX Unsigned32 (1..65535)
MAX-ACCESS read-only
STATUS current
DESCRIPTION
"This is a control variable.
It is written by the SME when the device is initialized.
The maximum time in TU that the transmitter is permitted to operate on a
single channel."
::= { dot11PhyFHSSEntry 3 }
dot11CurrentDwellTime OBJECT-TYPE
SYNTAX Unsigned32 (1..65535)
MAX-ACCESS read-write
STATUS current
DESCRIPTION
"This is a control variable.
In a non-AP STA, it is written by the MAC when it receives an FH Parameter
Set element, and changes take effect as soon as practical in the implementation.
In an AP, it is written by an external management entity, and changes take
effect for the next Beacon.
The current time in TU that the transmitter operates on a single channel,
as set by the MAC."
DEFVAL { 19 }
::= { dot11PhyFHSSEntry 4 }
dot11CurrentSet OBJECT-TYPE
SYNTAX Unsigned32 (1..255)
MAX-ACCESS read-write
STATUS current
DESCRIPTION
"This is a control variable.
It is written by an external management entity.
Changes take effect as soon as practical in the implementation.
The current set of patterns the PLME is using to determine the hopping
sequence. "
::= { dot11PhyFHSSEntry 5 }
dot11CurrentPattern OBJECT-TYPE
SYNTAX Unsigned32 (0..255)
MAX-ACCESS read-write
STATUS current
DESCRIPTION
"This is a control variable.
It is written by an external management entity.
Changes take effect as soon as practical in the implementation.
The current pattern the PLME is using to determine the hop sequence."
::= { dot11PhyFHSSEntry 6 }
dot11CurrentIndex OBJECT-TYPE
SYNTAX Unsigned32 (1..255)
MAX-ACCESS read-only
STATUS current
DESCRIPTION
"This is a status variable.
It is written by the PHY.
The current index value the PLME is using to determine the CurrentChannel-
Number."
::= { dot11PhyFHSSEntry 7 }
dot11EHCCPrimeRadix OBJECT-TYPE
SYNTAX Unsigned32
MAX-ACCESS read-write
STATUS current
DESCRIPTION
"This is a control variable.
It is written by an external management entity.
Changes take effect as soon as practical in the implementation.
This attribute indicates the value to be used as the prime radix (N) in
the HCC and EHCC algorithms."
::= { dot11PhyFHSSEntry 8 }
dot11EHCCNumberofChannelsFamilyIndex OBJECT-TYPE
SYNTAX Unsigned32
MAX-ACCESS read-write
STATUS current
DESCRIPTION
"This is a control variable.
It is written by an external management entity.
Changes take effect as soon as practical in the implementation.
This attribute indicates the value to be used as the maximum for the family
index (a) in the HCC and EHCC algorithms. The value of this field is
not less than the prime radix minus 3 (N - 3). The valid range of allowed
values is (N - 1), (N - 2), and (N - 3)."
::= { dot11PhyFHSSEntry 9 }
dot11EHCCCapabilityImplemented OBJECT-TYPE
SYNTAX TruthValue
MAX-ACCESS read-only
STATUS current
DESCRIPTION
"This is a capability variable.
Its value is determined by device capabilities.
This attribute, when true, indicates that the station implementation is
capable of generating the HCC or EHCC algorithms for determining Hopping
patterns. The capability is disabled, otherwise."
DEFVAL { false }
::= { dot11PhyFHSSEntry 10 }
dot11EHCCCapabilityActivated OBJECT-TYPE
SYNTAX TruthValue
MAX-ACCESS read-write
STATUS current
DESCRIPTION
"This is a control variable.
It is written by an external management entity.
Changes take effect for the next MLME-START.request primitive or MLMEJOIN.
request primitive.
This attribute, when true, indicates that the capability of the station to
operate using the HCC or EHCC algorithms for determining Hopping Patterns
is enabled. The capability is disabled, otherwise."
DEFVAL { false }
::= { dot11PhyFHSSEntry 11 }
dot11HopAlgorithmAdopted OBJECT-TYPE
SYNTAX INTEGER { crnt(1), hopindex(2), hcc(3) }
MAX-ACCESS read-write
STATUS current
DESCRIPTION
"This is a control variable.
It is written by an external management entity.
Changes take effect as soon as practical in the implementation.
This attribute, indicates which of the algorithms is used to generate the
Hopping Patterns.
Valid values are:
1 - hopping patterns as defined in Clause 14
2 - hop index method (with or without table)
3 - HCC/EHCC method"
::= { dot11PhyFHSSEntry 12 }
dot11RandomTableFlag OBJECT-TYPE
SYNTAX TruthValue
MAX-ACCESS read-write
STATUS current
DESCRIPTION
"This is a control variable.
It is written by an external management entity.
Changes take effect as soon as practical in the implementation.
This attribute, indicates that a Random Table is present when the value is
true. When the value is false it indicates that a Random Table is not
present and that the hop index method is to be used to determine the hopping
sequence."
DEFVAL { true }
::= { dot11PhyFHSSEntry 13 }
dot11NumberofHoppingSets OBJECT-TYPE
SYNTAX Unsigned32
MAX-ACCESS read-only
STATUS current
DESCRIPTION
"This is a control variable.
It is written by the SME when the device is initialized.
The Number of Sets field indicates the total number of sets within the
hopping patterns."
::= { dot11PhyFHSSEntry 14 }
dot11HopModulus OBJECT-TYPE
SYNTAX Unsigned32
MAX-ACCESS read-only
STATUS current
DESCRIPTION
"This is a control variable.
It is written by the SME when the device is initialized.
The number of allowed channels for the hopping set. This is defined by the
governing regulatory agency for the country code of the country in which
this device is operating."
::= { dot11PhyFHSSEntry 15 }
dot11HopOffset OBJECT-TYPE
SYNTAX Unsigned32
MAX-ACCESS read-write
STATUS current
DESCRIPTION
"This is a status variable.
It is written by the PHY.
The next position in the hopping set."
::= { dot11PhyFHSSEntry 16 }
-- **********************************************************************
-- * End of dot11PhyFHSS TABLE
-- **********************************************************************
-- **********************************************************************
-- * dot11PhyDSSSEntry TABLE
-- **********************************************************************
dot11PhyDSSSTable OBJECT-TYPE
SYNTAX SEQUENCE OF Dot11PhyDSSSEntry
MAX-ACCESS not-accessible
STATUS current
DESCRIPTION
"Entry of attributes for dot11PhyDSSSEntry. Implemented as a table indexed
on ifIndex to allow for multiple instances on an Agent."
::= { dot11phy 5 }
dot11PhyDSSSEntry OBJECT-TYPE
SYNTAX Dot11PhyDSSSEntry
MAX-ACCESS not-accessible
STATUS current
DESCRIPTION
"An entry in the dot11PhyDSSSEntry Table.
ifIndex - Each IEEE 802.11 interface is represented by an ifEntry. Interface
tables in this MIB module are indexed by ifIndex."
INDEX { ifIndex }
::= { dot11PhyDSSSTable 1 }
Dot11PhyDSSSEntry ::=
SEQUENCE {
dot11CurrentChannel Unsigned32,
dot11CCAModeSupported Unsigned32,
dot11CurrentCCAMode INTEGER,
dot11EDThreshold Integer32 }
dot11CurrentChannel OBJECT-TYPE
SYNTAX Unsigned32 (1..14)
MAX-ACCESS read-only
STATUS current
DESCRIPTION
"This is a status variable.
It is written by the PHY.
The current operating frequency channel of the DSSS PHY. Valid channel
numbers are as defined in 16.4.6.3"
::= { dot11PhyDSSSEntry 1 }
dot11CCAModeSupported OBJECT-TYPE
SYNTAX Unsigned32 (1..7)
MAX-ACCESS read-only
STATUS current
DESCRIPTION
"This is a capability variable.
Its value is determined by device capabilities.
dot11CCAModeSupported is a bit-significant value, representing all of the
CCA modes supported by the PHY. Valid values are:
energy detect only (ED_ONLY) = 01,
carrier sense only (CS_ONLY) = 02,
carrier sense and energy detect (ED_and_CS)= 04
This attribute is not used to indicate the CCA modes supported by a higher
rate extension PHY. Rather, the dot11HRCCAModeImplemented attribute is
used to indicate the CCA modes of the higher rate extension PHY."
::= { dot11PhyDSSSEntry 2 }
dot11CurrentCCAMode OBJECT-TYPE
SYNTAX INTEGER {
edonly(1),
csonly(2),
edandcs(4), cswithtimer(8),
hrcsanded(16) }
MAX-ACCESS read-write
STATUS current
DESCRIPTION
"This is a control variable.
It is written by an external management entity.
Changes take effect as soon as practical in the implementation.
The current CCA method in operation. Valid values are:
energy detect only (edonly) = 01,
carrier sense only (csonly) = 02,
carrier sense and energy detect (edandcs)= 04
carrier sense with timer (cswithtimer)= 08
high rate carrier sense and energy detect (hrcsanded)=16."
::= { dot11PhyDSSSEntry 3 }
dot11EDThreshold OBJECT-TYPE
SYNTAX Integer32
MAX-ACCESS read-write
STATUS current
DESCRIPTION
"This is a control variable.
It is written by an external management entity.
Changes take effect as soon as practical in the implementation.
The current Energy Detect Threshold being used by the DSSS PHY."
::= { dot11PhyDSSSEntry 4 }
-- **********************************************************************
-- * End of dot11PhyDSSSEntry TABLE
-- **********************************************************************
-- **********************************************************************
-- * dot11PhyIR TABLE
-- **********************************************************************
dot11PhyIRTable OBJECT-TYPE
SYNTAX SEQUENCE OF Dot11PhyIREntry
MAX-ACCESS not-accessible
STATUS current
DESCRIPTION
"Group of attributes for dot11PhyIRTable. Implemented as a table indexed
on ifIndex to allow for multiple instances on an Agent."
::= { dot11phy 6 }
dot11PhyIREntry OBJECT-TYPE
SYNTAX Dot11PhyIREntry
MAX-ACCESS not-accessible
STATUS current
DESCRIPTION
"An entry in the dot11PhyIR Table.
ifIndex - Each IEEE 802.11 interface is represented by an ifEntry. Interface
tables in this MIB module are indexed by ifIndex."
INDEX { ifIndex }
::= { dot11PhyIRTable 1 }
Dot11PhyIREntry ::=
SEQUENCE {
dot11CCAWatchdogTimerMax Unsigned32,
dot11CCAWatchdogCountMax Unsigned32,
dot11CCAWatchdogTimerMin Unsigned32,
dot11CCAWatchdogCountMin Unsigned32 }
dot11CCAWatchdogTimerMax OBJECT-TYPE
SYNTAX Unsigned32
MAX-ACCESS read-write
STATUS current
DESCRIPTION
"This is a control variable.
It is written by an external management entity.
Changes take effect as soon as practical in the implementation.
This parameter, together with CCAWatchdogCountMax, determines when energy
detected in the channel can be ignored."
::= { dot11PhyIREntry 1 }
dot11CCAWatchdogCountMax OBJECT-TYPE
SYNTAX Unsigned32
MAX-ACCESS read-write
STATUS current
DESCRIPTION
"This is a control variable.
It is written by an external management entity.
Changes take effect as soon as practical in the implementation.
This parameter, together with CCAWatchdogTimerMax, determines when energy
detected in the channel can be ignored."
::= { dot11PhyIREntry 2 }
dot11CCAWatchdogTimerMin OBJECT-TYPE
SYNTAX Unsigned32
MAX-ACCESS read-write
STATUS current
DESCRIPTION
"This is a control variable.
It is written by an external management entity.
Changes take effect as soon as practical in the implementation.
The minimum value to which CCAWatchdogTimerMax can be set."
::= { dot11PhyIREntry 3 }
dot11CCAWatchdogCountMin OBJECT-TYPE
SYNTAX Unsigned32
MAX-ACCESS read-write
STATUS current
DESCRIPTION
"This is a control variable.
It is written by an external management entity.
Changes take effect as soon as practical in the implementation.
The minimum value to which CCAWatchdogCount can be set."
::= { dot11PhyIREntry 4 }
-- **********************************************************************
-- * End of dot11PhyIR TABLE
-- **********************************************************************
-- **********************************************************************
-- * dot11RegDomainsSupported TABLE
-- **********************************************************************
dot11RegDomainsSupportedTable OBJECT-TYPE
SYNTAX SEQUENCE OF Dot11RegDomainsSupportedEntry
MAX-ACCESS not-accessible
STATUS deprecated
DESCRIPTION
"Superceded by dot11OperatingClassesTable.
There are different operational requirements dependent on the regulatory
domain. This attribute list describes the regulatory domains the PLCP and
PMD support in this implementation. Currently defined values and their
corresponding Regulatory Domains are:
FCC (USA) = X'10', DOC (Canada) = X'20', ETSI (most of Europe) = X'30',
Spain = X'31', France = X'32', Japan = X'40', China = X'50', Other = X'00'
"
::= { dot11phy 7}
dot11RegDomainsSupportedEntry OBJECT-TYPE
SYNTAX Dot11RegDomainsSupportedEntry
MAX-ACCESS not-accessible
STATUS deprecated
DESCRIPTION
"Superceded by dot11OperatingClassesTable.
An entry in the dot11RegDomainsSupportedTable.
ifIndex - Each IEEE 802.11 interface is represented by an ifEntry. Interface
tables in this MIB module are indexed by ifIndex."
INDEX { ifIndex, dot11RegDomainsSupportedIndex }
::= { dot11RegDomainsSupportedTable 1 }
Dot11RegDomainsSupportedEntry ::=
SEQUENCE {
dot11RegDomainsSupportedIndex Unsigned32,
dot11RegDomainsImplementedValue INTEGER }
dot11RegDomainsSupportedIndex OBJECT-TYPE
SYNTAX Unsigned32
MAX-ACCESS not-accessible
STATUS deprecated
DESCRIPTION
"The auxiliary variable used to identify instances of the columnar objects
in the RegDomainsSupport Table."
::= { dot11RegDomainsSupportedEntry 1 }
dot11RegDomainsImplementedValue OBJECT-TYPE
SYNTAX INTEGER {
other (0),
fcc(16),
doc(32),
etsi(48),
spain (49),
france(50),
japan (64)}
MAX-ACCESS read-only
STATUS deprecated
DESCRIPTION
"This is a capability variable.
Its value is determined by device capabilities.
There are different operational requirements dependent on the regulatory
domain. This attribute list describes the regulatory domains the PLCP and
PMD support in this implementation. Currently defined values and their
corresponding Regulatory Domains are:
FCC (USA) = X'10', DOC (Canada) = X'20', ETSI (most of Europe) = X'30',
Spain = X'31', France = X'32', Japan = X'40', China = X'50' "
::= { dot11RegDomainsSupportedEntry 2 }
-- **********************************************************************
-- * End of dot11RegDomainsSupported TABLE
-- **********************************************************************
-- **********************************************************************
-- * dot11AntennasList TABLE
-- **********************************************************************
dot11AntennasListTable OBJECT-TYPE
SYNTAX SEQUENCE OF Dot11AntennasListEntry
MAX-ACCESS not-accessible
STATUS current
DESCRIPTION
"This table represents the list of antennae. An antenna can be marked to
be capable of transmitting, receiving, and/or for participation in receive
diversity. Each entry in this table represents a single antenna with its
properties. The maximum number of antennae that can be contained in this
table is 255."
::= { dot11phy 8 }
dot11AntennasListEntry OBJECT-TYPE
SYNTAX Dot11AntennasListEntry
MAX-ACCESS not-accessible
STATUS current
DESCRIPTION
"An entry in the dot11AntennasListTable, representing the properties of a
single antenna.
ifIndex - Each IEEE 802.11 interface is represented by an ifEntry. Interface
tables in this MIB module are indexed by ifIndex."
INDEX { ifIndex, dot11AntennaListIndex }
::= { dot11AntennasListTable 1 }
Dot11AntennasListEntry ::=
SEQUENCE {
dot11AntennaListIndex Unsigned32,
dot11TxAntennaImplemented TruthValue,
dot11RxAntennaImplemented TruthValue,
dot11DiversitySelectionRxImplemented TruthValue }
dot11AntennaListIndex OBJECT-TYPE
SYNTAX Unsigned32 (1..255)
MAX-ACCESS not-accessible
STATUS current
DESCRIPTION
"The unique index of an antenna which is used to identify the columnar
objects in the dot11AntennasList Table."
::= { dot11AntennasListEntry 1 }
dot11TxAntennaImplemented OBJECT-TYPE
SYNTAX TruthValue
MAX-ACCESS read-only
STATUS current
DESCRIPTION
"This is a capability variable.
Its value is determined by device capabilities.
When true, this object indicates that the antenna represented by
dot11AntennaIndex can be used as a transmit antenna."
::= { dot11AntennasListEntry 2 }
dot11RxAntennaImplemented OBJECT-TYPE
SYNTAX TruthValue
MAX-ACCESS read-only
STATUS current
DESCRIPTION
"This is a capability variable.
Its value is determined by device capabilities.
When true, this object indicates that the antenna represented by the
dot11AntennaIndex can be used as a receive antenna."
::= { dot11AntennasListEntry 3 }
dot11DiversitySelectionRxImplemented OBJECT-TYPE
SYNTAX TruthValue
MAX-ACCESS read-only
STATUS current
DESCRIPTION
"This is a capability variable.
Its value is determined by device capabilities.
When true, this object indicates that the antenna represented by
dot11AntennaIndex can be used for receive diversity. This object is true
only if the antenna can be used as a receive antenna, as indicated by
dot11RxAntennaImplemented."
::= { dot11AntennasListEntry 4 }
-- **********************************************************************
-- * End of dot11AntennasList TABLE
-- **********************************************************************
-- **********************************************************************
-- * dot11SupportedDataRatesTx TABLE
-- **********************************************************************
dot11SupportedDataRatesTxTable OBJECT-TYPE
SYNTAX SEQUENCE OF Dot11SupportedDataRatesTxEntry
MAX-ACCESS not-accessible
STATUS current
DESCRIPTION
"The Transmit bit rates supported by the PLCP and PMD, represented by a
count from X'02-X'7f, corresponding to data rates in increments of
500kbit/s from 1 Mb/s to 63.5 Mb/s subject to limitations of each individual
PHY."
::= { dot11phy 9 }
dot11SupportedDataRatesTxEntry OBJECT-TYPE
SYNTAX Dot11SupportedDataRatesTxEntry
MAX-ACCESS not-accessible
STATUS current
DESCRIPTION
"An Entry (conceptual row) in the dot11SupportedDataRatesTx Table.
ifIndex - Each IEEE 802.11 interface is represented by an ifEntry. Interface
tables in this MIB module are indexed by ifIndex."
INDEX { ifIndex, dot11SupportedDataRatesTxIndex }
::= { dot11SupportedDataRatesTxTable 1 }
Dot11SupportedDataRatesTxEntry ::=
SEQUENCE {
dot11SupportedDataRatesTxIndex Unsigned32,
dot11ImplementedDataRatesTxValue Unsigned32 }
dot11SupportedDataRatesTxIndex OBJECT-TYPE
SYNTAX Unsigned32 (1..255)
MAX-ACCESS not-accessible
STATUS current
DESCRIPTION
"Index object that identifies which data rate to access. Range is 1..255."
::= { dot11SupportedDataRatesTxEntry 1 }
dot11ImplementedDataRatesTxValue OBJECT-TYPE
SYNTAX Unsigned32 (2..127)
MAX-ACCESS read-only
STATUS current
DESCRIPTION
"This is a capability variable.
Its value is determined by device capabilities.
The Transmit bit rates supported by the PLCP and PMD, represented by a
count from X'02-X'7f, corresponding to data rates in increments of
500kbit/s from 1 Mb/s to 63.5 Mb/s subject to limitations of each individual
PHY."
::= { dot11SupportedDataRatesTxEntry 2 }
-- **********************************************************************
-- * End of dot11SupportedDataRatesTx TABLE
-- **********************************************************************
-- **********************************************************************
-- * dot11SupportedDataRatesRx TABLE
-- **********************************************************************
dot11SupportedDataRatesRxTable OBJECT-TYPE
SYNTAX SEQUENCE OF Dot11SupportedDataRatesRxEntry
MAX-ACCESS not-accessible
STATUS current
DESCRIPTION
"The receive bit rates supported by the PLCP and PMD, represented by a
count from X'002-X'7f, corresponding to data rates in increments of
500kbit/s from 1 Mb/s to 63.5 Mb/s."
::= { dot11phy 10 }
dot11SupportedDataRatesRxEntry OBJECT-TYPE
SYNTAX Dot11SupportedDataRatesRxEntry
MAX-ACCESS not-accessible
STATUS current
DESCRIPTION
"An Entry (conceptual row) in the dot11SupportedDataRatesRx Table.
ifIndex - Each IEEE 802.11 interface is represented by an ifEntry. Interface
tables in this MIB module are indexed by ifIndex."
INDEX { ifIndex, dot11SupportedDataRatesRxIndex }
::= { dot11SupportedDataRatesRxTable 1 }
Dot11SupportedDataRatesRxEntry ::=
SEQUENCE {
dot11SupportedDataRatesRxIndex Unsigned32,
dot11ImplementedDataRatesRxValue Unsigned32 }
dot11SupportedDataRatesRxIndex OBJECT-TYPE
SYNTAX Unsigned32 (1..255)
MAX-ACCESS not-accessible
STATUS current
DESCRIPTION
"Index object that identifies which data rate to access. Range is 1..255."
::= { dot11SupportedDataRatesRxEntry 1 }
dot11ImplementedDataRatesRxValue OBJECT-TYPE
SYNTAX Unsigned32 (2..127)
MAX-ACCESS read-only
STATUS current
DESCRIPTION
"This is a capability variable.
Its value is determined by device capabilities.
The receive bit rates supported by the PLCP and PMD, represented by a
count from X'02-X'7f, corresponding to data rates in increments of
500kbit/s from 1 Mb/s to 63.5 Mb/s."
::= { dot11SupportedDataRatesRxEntry 2 }
-- **********************************************************************
-- * End of dot11SupportedDataRatesRx TABLE
-- **********************************************************************
-- **********************************************************************
-- * dot11PhyOFDM TABLE
-- **********************************************************************
dot11PhyOFDMTable OBJECT-TYPE
SYNTAX SEQUENCE OF Dot11PhyOFDMEntry
MAX-ACCESS not-accessible
STATUS current
DESCRIPTION
"Group of attributes for dot11PhyOFDMTable. Implemented as a table indexed
on ifindex to allow for multiple instances on an Agent."
::= { dot11phy 11 }
dot11PhyOFDMEntry OBJECT-TYPE
SYNTAX Dot11PhyOFDMEntry
MAX-ACCESS not-accessible
STATUS current
DESCRIPTION
"An entry in the dot11PhyOFDM Table.
ifIndex - Each IEEE 802.11 interface is represented by an ifEntry. Interface
tables in this MIB module are indexed by ifIndex."
INDEX { ifIndex }
::= { dot11PhyOFDMTable 1 }
Dot11PhyOFDMEntry ::=
SEQUENCE {
dot11CurrentFrequency Unsigned32,
dot11TIThreshold Integer32,
dot11FrequencyBandsImplemented Unsigned32,
dot11ChannelStartingFactor Unsigned32,
dot11FiveMHzOperationImplemented TruthValue,
dot11TenMHzOperationImplemented TruthValue,
dot11TwentyMHzOperationImplemented TruthValue,
dot11PhyOFDMChannelWidth INTEGER,
dot11OFDMCCAEDImplemented TruthValue,
dot11OFDMCCAEDRequired TruthValue,
dot11OFDMEDThreshold Unsigned32,
dot11STATransmitPowerClass INTEGER,
dot11ACRType INTEGER }
dot11CurrentFrequency OBJECT-TYPE
SYNTAX Unsigned32 (0..200)
MAX-ACCESS read-only
STATUS current
DESCRIPTION
"This is a control variable.
It is written by the SME.
Changes take effect as soon as practical in the implementation.
The number of the current operating frequency channel of the OFDM PHY."
::= { dot11PhyOFDMEntry 1 }
dot11TIThreshold OBJECT-TYPE
SYNTAX Integer32
MAX-ACCESS read-write
STATUS deprecated
DESCRIPTION
"Superseded by PHY-specific or regulatory CCA energy detect limits.
The Threshold being used to detect a busy medium (frequency). CCA reports
a busy medium upon detecting the RSSI above this threshold."
::= { dot11PhyOFDMEntry 2 }
dot11FrequencyBandsImplemented OBJECT-TYPE
SYNTAX Unsigned32 (1..127)
MAX-ACCESS read-only
STATUS deprecated
DESCRIPTION
"Superseded by subband-specific supported operating classes.
This is a capability variable.
Its value is determined by device capabilities.
The capability of the OFDM PHY implementation to operate in the 4.9 GHz
and 5 GHz bands. Coded as an integer value with bit 0 LSB as follows:
bit 0 .. capable of operating in the 5.15-5.25 GHz band
bit 1 .. capable of operating in the 5.25-5.35 GHz band
bit 2 .. capable of operating in the 5.725-5.825 GHz band
bit 3 .. capable of operating in the 5.47-5.725 GHz band
bit 4 .. capable of operating in the lower Japanese (5.15-5.25 GHz) band
bit 5 .. capable of operating in the 5.03-5.091 GHz band
bit 6 .. capable of operating in the 4.94-4.99 GHz band
For example, for an implementation capable of operating in the 5.15-5.35
GHz bands this attribute would take the value 3."
::= { dot11PhyOFDMEntry 3 }
dot11ChannelStartingFactor OBJECT-TYPE
SYNTAX Unsigned32 (8000..10000)
MAX-ACCESS read-write
STATUS current
DESCRIPTION
"This is a control variable.
It is written by an external management entity.
Changes take effect as soon as practical in the implementation.
The base factor from which channel center frequencies are calculated. This
number is multiplied by 500 kHz to form the base frequency to be added to
the channel number x 5 MHz."
DEFVAL { 10000 }
::= { dot11PhyOFDMEntry 4 }
dot11FiveMHzOperationImplemented OBJECT-TYPE
SYNTAX TruthValue
MAX-ACCESS read-only
STATUS current
DESCRIPTION
"This is a capability variable.
Its value is determined by device capabilities.
This attribute, when true, indicates that the 5 MHz Operation is implemented."
DEFVAL { false }
::= { dot11PhyOFDMEntry 5 }
dot11TenMHzOperationImplemented OBJECT-TYPE
SYNTAX TruthValue
MAX-ACCESS read-only
STATUS current
DESCRIPTION
"This is a capability variable.
Its value is determined by device capabilities.
This attribute, when true, indicates that the 10 MHz Operation is implemented."
DEFVAL { false }
::= { dot11PhyOFDMEntry 6 }
dot11TwentyMHzOperationImplemented OBJECT-TYPE
SYNTAX TruthValue
MAX-ACCESS read-only
STATUS current
DESCRIPTION
"This is a capability variable.
Its value is determined by device capabilities.
This attribute, when true, indicates that the 20 MHz Operation is implemented."
DEFVAL { true }
::= { dot11PhyOFDMEntry 7 }
dot11PhyOFDMChannelWidth OBJECT-TYPE
SYNTAX INTEGER { width5MHz(1), width10MHz(2), width20MHz(3)}
MAX-ACCESS read-only
STATUS current
DESCRIPTION
"This is a control variable.
It is written by the SME.
Changes take effect as soon as practical in the implementation.
This is an 8-bit integer value that identifies the OFDM PHY channel width.
Currently defined values and their corresponding Channel widths are:
5MHz = 01, 10MHz = 02, 20MHz = 03"
::= { dot11PhyOFDMEntry 8 }
dot11OFDMCCAEDImplemented OBJECT-TYPE
SYNTAX TruthValue
MAX-ACCESS read-only
STATUS current
DESCRIPTION
"This is a capability variable.
Its value is determined by device capabilities.
This attribute indicates that the OFDM PHY is capable of CCA-Energy
Detect."
::= { dot11PhyOFDMEntry 9 }
dot11OFDMCCAEDRequired OBJECT-TYPE
SYNTAX TruthValue
MAX-ACCESS read-only
STATUS current
DESCRIPTION
"This is a control variable.
It is written by the SME when the device is initialized for operation in a
band defined by an Operating Class.
This attribute indicates that the PHY CCA-Energy Detect functionality is
enabled."
::= { dot11PhyOFDMEntry 10 }
dot11OFDMEDThreshold OBJECT-TYPE
SYNTAX Unsigned32 (0..255)
MAX-ACCESS read-write
STATUS current
DESCRIPTION
"This is a control variable.
It is written the SME when the device is initialized for operation in a
band defined by an Operating Class, or written by an external management
entity.
Changes take effect as soon as practical in the implementation.
The current Energy Detect Threshold being used by the OFDM PHY."
::= { dot11PhyOFDMEntry 11 }
dot11STATransmitPowerClass OBJECT-TYPE
SYNTAX INTEGER { classA(1), classB(2), classC(3), classD(4) }
MAX-ACCESS read-write
STATUS current
DESCRIPTION
"The station transmit power class: Class A=1, Class B=2, Class C=3, Class
D=4 (as defined in D.2.2)."
DEFVAL { 1 }
::= { dot11PhyOFDMEntry 12 }
dot11ACRType OBJECT-TYPE
SYNTAX INTEGER { standard(1), enhanced(2) }
MAX-ACCESS read-only
STATUS current
DESCRIPTION
"This is a status variable.
It is written by the SME.
The Adjacent and Nonadjacent Channel Rejection performance:
when this attribute = 1 the levels in Table 18-14 apply; when this attribute
= 2 the levels in Table 18-15 apply."
DEFVAL { 1 }
::= { dot11PhyOFDMEntry 13 }
-- **********************************************************************
-- * End of dot11PhyOFDM TABLE
-- **********************************************************************
-- **********************************************************************
-- * dot11PhyHRDSSSEntry TABLE
-- **********************************************************************
dot11PhyHRDSSSTable OBJECT-TYPE
SYNTAX SEQUENCE OF Dot11PhyHRDSSSEntry
MAX-ACCESS not-accessible
STATUS current
DESCRIPTION
"Entry of attributes for dot11PhyHRDSSSEntry. Implemented as a table
indexed on ifIndex to allow for multiple instances on an Agent."
::= { dot11phy 12 }
dot11PhyHRDSSSEntry OBJECT-TYPE
SYNTAX Dot11PhyHRDSSSEntry
MAX-ACCESS not-accessible
STATUS current
DESCRIPTION
"An entry in the dot11PhyHRDSSSEntry Table.
ifIndex - Each IEEE 802.11 interface is represented by an ifEntry. Interface
tables in this MIB module are indexed by ifIndex."
INDEX { ifIndex }
::= { dot11PhyHRDSSSTable 1 }
Dot11PhyHRDSSSEntry ::=
SEQUENCE {
dot11ShortPreambleOptionImplemented TruthValue,
dot11PBCCOptionImplemented TruthValue,
dot11ChannelAgilityPresent TruthValue,
dot11ChannelAgilityActivated TruthValue,
dot11HRCCAModeImplemented Unsigned32 }
dot11ShortPreambleOptionImplemented OBJECT-TYPE
SYNTAX TruthValue
MAX-ACCESS read-only
STATUS current
DESCRIPTION
"This is a capability variable.
Its value is determined by device capabilities.
This attribute, when true, indicates that the short preamble option as
defined in 17.2.2.3 is implemented."
DEFVAL { false }
::= { dot11PhyHRDSSSEntry 1 }
dot11PBCCOptionImplemented OBJECT-TYPE
SYNTAX TruthValue
MAX-ACCESS read-only
STATUS current
DESCRIPTION
"This is a capability variable.
Its value is determined by device capabilities.
This attribute, when true, indicates that the PBCC modulation option as
defined in 17.4.6.7 is implemented."
DEFVAL { false }
::= { dot11PhyHRDSSSEntry 2 }
dot11ChannelAgilityPresent OBJECT-TYPE
SYNTAX TruthValue
MAX-ACCESS read-only
STATUS current
DESCRIPTION
"This is a capability variable.
Its value is determined by device capabilities.
This attribute indicates that the PHY is capable of channel agility."
::= { dot11PhyHRDSSSEntry 3 }
dot11ChannelAgilityActivated OBJECT-TYPE
SYNTAX TruthValue
MAX-ACCESS read-write
STATUS current
DESCRIPTION
"This is a control variable.
It is written by an external management entity.
Changes take effect for the next MLME-START.request primitive or MLMEJOIN.
request primitive.
This attribute indicates that the PHY channel agility functionality is
enabled."
::= { dot11PhyHRDSSSEntry 4 }
dot11HRCCAModeImplemented OBJECT-TYPE
SYNTAX Unsigned32 (1..31)
MAX-ACCESS read-only
STATUS current
DESCRIPTION
"This is a capability variable.
Its value is determined by device capabilities.
dot11HRCCAModeImplemented is a bit-significant value, representing all of
the CCA modes supported by the PHY. Valid values are:
energy detect only (ED_ONLY) = 01,
carrier sense only (CS_ONLY) = 02,
carrier sense and energy detect (ED_and_CS)= 04,
carrier sense with timer (CS_and_Timer)= 08,
high rate carrier sense and energy detect (HRCS_and_ED)= 16
or the logical sum of any of these values. In the high rate extension PHY,
this attribute is used in preference to the dot11CCAModeSupported attribute."
::= { dot11PhyHRDSSSEntry 5 }
-- **********************************************************************
-- * End of dot11PhyHRDSSSEntry TABLE
-- **********************************************************************
-- **********************************************************************
-- * dot11HoppingPattern TABLE
-- **********************************************************************
dot11HoppingPatternTable OBJECT-TYPE
SYNTAX SEQUENCE OF Dot11HoppingPatternEntry
MAX-ACCESS not-accessible
STATUS current
DESCRIPTION
"The (conceptual) table of attributes necessary for a frequency hopping
implementation to be able to create the hopping sequences necessary to
operate in the subband for the associated domain country string."
::= { dot11phy 13 }
dot11HoppingPatternEntry OBJECT-TYPE
SYNTAX Dot11HoppingPatternEntry
MAX-ACCESS not-accessible
STATUS current
DESCRIPTION
"An entry (conceptual row) in the Hopping Pattern Table that indicates the
random hopping sequence to be followed.
IfIndex - Each IEEE 802.11 interface is represented by an ifEntry. Interface
tables in this MIB are indexed by ifIndex."
INDEX { ifIndex, dot11HoppingPatternIndex }
::= { dot11HoppingPatternTable 1 }
Dot11HoppingPatternEntry ::=
SEQUENCE {
dot11HoppingPatternIndex Unsigned32,
dot11RandomTableFieldNumber Unsigned32 }
dot11HoppingPatternIndex OBJECT-TYPE
SYNTAX Unsigned32
MAX-ACCESS not-accessible
STATUS current
DESCRIPTION
"The auxiliary variable used to identify instances of the columnar objects
in the Hopping Pattern Table."
::= { dot11HoppingPatternEntry 1 }
dot11RandomTableFieldNumber OBJECT-TYPE
SYNTAX Unsigned32
MAX-ACCESS read-only
STATUS current
DESCRIPTION
"This is a control variable.
It is written by the SME when the device is initialized.
This attribute indicates the value of the starting channel number in the
hopping sequence of the subband for the associated domain country string."
DEFVAL { 0 }
::= { dot11HoppingPatternEntry 2 }
-- **********************************************************************
-- * End of dot11HoppingPattern TABLE
-- **********************************************************************
-- **********************************************************************
-- * dot11PhyERP TABLE
-- **********************************************************************
dot11PhyERPTable OBJECT-TYPE
SYNTAX SEQUENCE OF Dot11PhyERPEntry
MAX-ACCESS not-accessible
STATUS current
DESCRIPTION
"Entry of attributes for dot11PhyERPEntry. Implemented as a table indexed
on ifIndex to allow for multiple instances on an Agent."
::= { dot11phy 14 }
dot11PhyERPEntry OBJECT-TYPE
SYNTAX Dot11PhyERPEntry
MAX-ACCESS not-accessible
STATUS current
DESCRIPTION
"An entry in the dot11PhyERPEntry Table.
ifIndex - Each 802.11 interface is represented by an ifEntry. Interface
tables in this MIB module are indexed by ifIndex."
INDEX {ifIndex}
::= { dot11PhyERPTable 1 }
Dot11PhyERPEntry ::=
SEQUENCE {
dot11ERPPBCCOptionImplemented TruthValue,
dot11ERPBCCOptionActivated TruthValue,
dot11DSSSOFDMOptionImplemented TruthValue,
dot11DSSSOFDMOptionActivated TruthValue,
dot11ShortSlotTimeOptionImplemented TruthValue,
dot11ShortSlotTimeOptionActivated TruthValue }
dot11ERPPBCCOptionImplemented OBJECT-TYPE
SYNTAX TruthValue
MAX-ACCESS read-only
STATUS current
DESCRIPTION
"This is a capability variable.
Its value is determined by device capabilities.
This attribute, when true, indicates that the ERP-PBCC modulation option
as defined in 18.6 (ERP-PBCC operation specifications) is implemented."
DEFVAL { false }
::= { dot11PhyERPEntry 1 }
dot11ERPBCCOptionActivated OBJECT-TYPE
SYNTAX TruthValue
MAX-ACCESS read-write
STATUS current
DESCRIPTION
"This is a control variable.
It is written by an external management entity.
Changes take effect for the next MLME-START.request or MLME-JOIN.request.
This attribute, when true, indicates that the ERP-PBCC option as defined
in 18.6 (ERP-PBCC operation specifications) is enabled."
DEFVAL { false }
::= { dot11PhyERPEntry 2 }
dot11DSSSOFDMOptionImplemented OBJECT-TYPE
SYNTAX TruthValue
MAX-ACCESS read-only
STATUS current
DESCRIPTION
"This is a capability variable.
Its value is determined by device capabilities.
This attribute, when true, indicates that the DSSS-OFDM option as defined
in 18.7 (DSSS-OFDM operation specifications) is implemented."
DEFVAL { false }
::= { dot11PhyERPEntry 3 }
dot11DSSSOFDMOptionActivated OBJECT-TYPE
SYNTAX TruthValue
MAX-ACCESS read-write
STATUS current
DESCRIPTION
"This is a control variable.
It is written by an external management entity.
Changes take effect for the next MLME-START.request primitive or MLMEJOIN.
request primitive.
This attribute, when true, indicates that the DSSS-OFDM option as defined
in 18.7 (DSSS-OFDM operation specifications) is enabled."
DEFVAL { false }
::= { dot11PhyERPEntry 4 }
dot11ShortSlotTimeOptionImplemented OBJECT-TYPE
SYNTAX TruthValue
MAX-ACCESS read-only
STATUS current
DESCRIPTION
"This is a capability variable.
Its value is determined by device capabilities.
This attribute, when true, indicates that the Short Slot Time option as
defined in 8.4.1.4 is implemented."
DEFVAL { false }
::= { dot11PhyERPEntry 5}
dot11ShortSlotTimeOptionActivated OBJECT-TYPE
SYNTAX TruthValue
MAX-ACCESS read-write
STATUS current
DESCRIPTION
"This is a control variable.
It is written by an external management entity.
Changes take effect as soon as practical in the implementation.
This attribute, when true, indicates that the Short Slot Time option as
defined in 8.4.1.4 is enabled."
DEFVAL { false }
::= { dot11PhyERPEntry 6 }
-- **********************************************************************
-- * End of dot11PhyERP TABLE
-- **********************************************************************
-- **********************************************************************
-- * dot11 Phy HT TABLE
-- **********************************************************************
dot11PhyHTTable OBJECT-TYPE
SYNTAX SEQUENCE OF Dot11PhyHTEntry
MAX-ACCESS not-accessible
STATUS current
DESCRIPTION
"Entry of attributes for dot11PhyHTTable. Implemented as a table indexed
on ifIndex to allow for multiple instances on an Agent."
::= { dot11phy 15 }
dot11PhyHTEntry OBJECT-TYPE
SYNTAX Dot11PhyHTEntry
MAX-ACCESS not-accessible
STATUS current
DESCRIPTION
"An entry in the dot11PhyHTEntry Table. ifIndex - Each IEEE 802.11 interface
is represented by an ifEntry. Interface tables in this MIB module are
indexed by ifIndex."
INDEX {ifIndex}
::= { dot11PhyHTTable 1 }
Dot11PhyHTEntry ::=
SEQUENCE {
dot11FortyMHzOperationImplemented TruthValue,
dot11FortyMHzOperationActivated TruthValue,
dot11CurrentPrimaryChannel Unsigned32,
dot11CurrentSecondaryChannel Unsigned32,
dot11NumberOfSpatialStreamsImplemented Unsigned32,
dot11NumberOfSpatialStreamsActivated Unsigned32,
dot11HTGreenfieldOptionImplemented TruthValue,
dot11HTGreenfieldOptionActivated TruthValue,
dot11ShortGIOptionInTwentyImplemented TruthValue,
dot11ShortGIOptionInTwentyActivated TruthValue,
dot11ShortGIOptionInFortyImplemented TruthValue,
dot11ShortGIOptionInFortyActivated TruthValue,
dot11LDPCCodingOptionImplemented TruthValue,
dot11LDPCCodingOptionActivated TruthValue,
dot11TxSTBCOptionImplemented TruthValue,
dot11TxSTBCOptionActivated TruthValue,
dot11RxSTBCOptionImplemented TruthValue,
dot11RxSTBCOptionActivated TruthValue,
dot11BeamFormingOptionImplemented TruthValue,
dot11BeamFormingOptionActivated TruthValue,
dot11HighestSupportedDataRate Unsigned32,
dot11TxMCSSetDefined TruthValue,
dot11TxRxMCSSetNotEqual TruthValue,
dot11TxMaximumNumberSpatialStreamsSupported Unsigned32,
dot11TxUnequalModulationSupported TruthValue }
dot11FortyMHzOperationImplemented OBJECT-TYPE
SYNTAX TruthValue
MAX-ACCESS read-only
STATUS current
DESCRIPTION
"This is a capability variable.
Its value is determined by device capabilities.
This attribute, when true, indicates that the 40 MHz Operation is implemented."
DEFVAL { false }
::= { dot11PhyHTEntry 1 }
dot11FortyMHzOperationActivated OBJECT-TYPE
SYNTAX TruthValue
MAX-ACCESS read-write
STATUS current
DESCRIPTION
"This is a control variable.
It is written by an external management entity.
Changes take effect as soon as practical in the implementation.
This attribute, when true, indicates that the 40 MHz Operation is
enabled."
DEFVAL { false }
::= { dot11PhyHTEntry 2 }
dot11CurrentPrimaryChannel OBJECT-TYPE
SYNTAX Unsigned32
MAX-ACCESS read-only
STATUS current
DESCRIPTION
"This is a status variable.
It is written by the PHY.
This attribute indicates the operating channel. If 20/40 MHz BSS is currently
in use then this attribute indicates the primary channel."
::= { dot11PhyHTEntry 3 }
dot11CurrentSecondaryChannel OBJECT-TYPE
SYNTAX Unsigned32
MAX-ACCESS read-only
STATUS current
DESCRIPTION
"This is a status variable.
It is written by the PHY.
This attribute indicates the channel number of the secondary channel. If
20/40 MHz BSS is not currently in use, this attribute value shall be 0."
::= { dot11PhyHTEntry 4 }
dot11NumberOfSpatialStreamsImplemented OBJECT-TYPE
SYNTAX Unsigned32 (1..4)
MAX-ACCESS read-only
STATUS current
DESCRIPTION
"This is a capability variable.
Its value is determined by device capabilities.
This attribute indicates the maximum number of spatial streams implemented."
DEFVAL { 2 }
::= { dot11PhyHTEntry 5 }
dot11NumberOfSpatialStreamsActivated OBJECT-TYPE
SYNTAX Unsigned32 (1..4)
MAX-ACCESS read-write
STATUS current
DESCRIPTION
"This is a control variable.
It is written by an external management entity.
Changes take effect as soon as practical in the implementation.
This attribute indicates the maximum number of spatial streams enabled."
DEFVAL { 2 }
::= { dot11PhyHTEntry 6 }
dot11HTGreenfieldOptionImplemented OBJECT-TYPE
SYNTAX TruthValue
MAX-ACCESS read-only
STATUS current
DESCRIPTION
"This is a capability variable.
Its value is determined by device capabilities.
This attribute, when true, indicates that the HT-greenfield option is
implemented."
DEFVAL { false }
::= { dot11PhyHTEntry 7 }
dot11HTGreenfieldOptionActivated OBJECT-TYPE
SYNTAX TruthValue
MAX-ACCESS read-write
STATUS current
DESCRIPTION
"This is a control variable.
It is written by an external management entity.
Changes take effect as soon as practical in the implementation.
This attribute, when true, indicates that the HT-greenfield option is
enabled."
DEFVAL { false }
::= { dot11PhyHTEntry 8 }
dot11ShortGIOptionInTwentyImplemented OBJECT-TYPE
SYNTAX TruthValue
MAX-ACCESS read-only
STATUS current
DESCRIPTION
"This is a capability variable.
Its value is determined by device capabilities.
This attribute, when true, indicates that the Short Guard option is implemented
for 20 MHz operation."
DEFVAL { false }
::= { dot11PhyHTEntry 9 }
dot11ShortGIOptionInTwentyActivated OBJECT-TYPE
SYNTAX TruthValue
MAX-ACCESS read-write
STATUS current
DESCRIPTION
"This is a control variable.
It is written by an external management entity.
Changes take effect as soon as practical in the implementation.
This attribute, when true, indicates that the Short Guard option is
enabled for 20 MHz operation."
DEFVAL { false }
::= { dot11PhyHTEntry 10 }
dot11ShortGIOptionInFortyImplemented OBJECT-TYPE
SYNTAX TruthValue
MAX-ACCESS read-only
STATUS current
DESCRIPTION
"This is a capability variable.
Its value is determined by device capabilities.
This attribute, when true, indicates that the Short Guard option is implemented
for 40 MHz operation."
DEFVAL { false }
::= { dot11PhyHTEntry 11 }
dot11ShortGIOptionInFortyActivated OBJECT-TYPE
SYNTAX TruthValue
MAX-ACCESS read-write
STATUS current
DESCRIPTION
"This is a control variable.
It is written by an external management entity.
Changes take effect as soon as practical in the implementation.
This attribute, when true, indicates that the Short Guard option is
enabled for 40 MHz operation."
DEFVAL { false }
::= { dot11PhyHTEntry 12 }
dot11LDPCCodingOptionImplemented OBJECT-TYPE
SYNTAX TruthValue
MAX-ACCESS read-only
STATUS current
DESCRIPTION
"This is a capability variable.
Its value is determined by device capabilities.
This attribute, when true, indicates that the LDPC coding option is implemented."
DEFVAL { false }
::= { dot11PhyHTEntry 13 }
dot11LDPCCodingOptionActivated OBJECT-TYPE
SYNTAX TruthValue
MAX-ACCESS read-write
STATUS current
DESCRIPTION
"This is a control variable.
It is written by an external management entity.
Changes take effect as soon as practical in the implementation.
This attribute, when true, indicates that the LDPC coding option is
enabled."
DEFVAL { false }
::= { dot11PhyHTEntry 14 }
dot11TxSTBCOptionImplemented OBJECT-TYPE
SYNTAX TruthValue
MAX-ACCESS read-only
STATUS current
DESCRIPTION
"This is a capability variable.
Its value is determined by device capabilities.
This attribute, when true, indicates that the entity is capable of transmitting
frames using STBC option."
DEFVAL { false }
::= { dot11PhyHTEntry 15 }
dot11TxSTBCOptionActivated OBJECT-TYPE
SYNTAX TruthValue
MAX-ACCESS read-write
STATUS current
DESCRIPTION
"This is a control variable.
It is written by an external management entity.
Changes take effect as soon as practical in the implementation.
This attribute, when true, indicates that the entity's capability of
transmitting frames using STBC option is enabled."
DEFVAL { false }
::= { dot11PhyHTEntry 16 }
dot11RxSTBCOptionImplemented OBJECT-TYPE
SYNTAX TruthValue
MAX-ACCESS read-only
STATUS current
DESCRIPTION
"This is a capability variable.
Its value is determined by device capabilities.
This attribute, when true, indicates that the entity is capable of receiving
frames that are sent using the STBC."
DEFVAL { false }
::= { dot11PhyHTEntry 17 }
dot11RxSTBCOptionActivated OBJECT-TYPE
SYNTAX TruthValue
MAX-ACCESS read-write
STATUS current
DESCRIPTION
"This is a control variable.
It is written by an external management entity.
Changes take effect as soon as practical in the implementation.
This attribute, when true, indicates that the entity's capability of
receiving frames that are sent using the STBC is enabled."
DEFVAL { false }
::= { dot11PhyHTEntry 18 }
dot11BeamFormingOptionImplemented OBJECT-TYPE
SYNTAX TruthValue
MAX-ACCESS read-only
STATUS current
DESCRIPTION
"This is a capability variable.
Its value is determined by device capabilities.
This attribute, when true, indicates that the beamforming option is implemented."
DEFVAL { false }
::= { dot11PhyHTEntry 19 }
dot11BeamFormingOptionActivated OBJECT-TYPE
SYNTAX TruthValue
MAX-ACCESS read-write
STATUS current
DESCRIPTION
"This is a control variable.
It is written by an external management entity.
Changes take effect as soon as practical in the implementation.
This attribute, when true, indicates that the beamforming option is
enabled."
DEFVAL { false }
::= { dot11PhyHTEntry 20 }
dot11HighestSupportedDataRate OBJECT-TYPE
SYNTAX Unsigned32 (0..600)
MAX-ACCESS read-only
STATUS current
DESCRIPTION
"This is a capability variable.
Its value is determined by device capabilities.
This attribute shall specify the Highest Data Rate in Mb/s at which the
station may receive data."
DEFVAL { 0 }
::= { dot11PhyHTEntry 21 }
dot11TxMCSSetDefined OBJECT-TYPE
SYNTAX TruthValue
MAX-ACCESS read-write
STATUS current
DESCRIPTION
"This is a control variable.
It is written by an external management entity.
Changes take effect as soon as practical in the implementation.
This attribute, when true, indicates that the Tx MCS set is defined."
DEFVAL { false }
::= { dot11PhyHTEntry 22 }
dot11TxRxMCSSetNotEqual OBJECT-TYPE
SYNTAX TruthValue
MAX-ACCESS read-only
STATUS current
DESCRIPTION
"This is a status variable.
It is written by the PHY.
This attribute, when true, indicates that the supported Tx and Rx MCS sets
are not equal."
DEFVAL { false }
::= { dot11PhyHTEntry 23 }
dot11TxMaximumNumberSpatialStreamsSupported OBJECT-TYPE
SYNTAX Unsigned32 (0..3)
MAX-ACCESS read-only
STATUS current
DESCRIPTION
"This is a capability variable.
Its value is determined by device capabilities.
This attribute indicates the Tx maximum number of spatial streams supported."
DEFVAL { 0 }
::= { dot11PhyHTEntry 24 }
dot11TxUnequalModulationSupported OBJECT-TYPE
SYNTAX TruthValue
MAX-ACCESS read-only
STATUS current
DESCRIPTION
"This is a capability variable.
Its value is determined by device capabilities.
This attribute, when true, indicates that Tx UEQM is supported."
DEFVAL { false }
::= { dot11PhyHTEntry 25 }
-- **********************************************************************
-- * End of dot11 PHY HT TABLE
-- **********************************************************************
-- **********************************************************************
-- * dot11 Supported MCS Tx TABLE
-- **********************************************************************
dot11SupportedMCSTxTable OBJECT-TYPE
SYNTAX SEQUENCE OF Dot11SupportedMCSTxEntry
MAX-ACCESS not-accessible
STATUS current
DESCRIPTION
"he Transmit MCS supported by the PLCP and PMD, represented by a count
from 1 to 127, subject to limitations of each individual PHY."
::= { dot11phy 16 }
dot11SupportedMCSTxEntry OBJECT-TYPE
SYNTAX Dot11SupportedMCSTxEntry
MAX-ACCESS not-accessible
STATUS current
DESCRIPTION
"An Entry (conceptual row) in the dot11SupportedMCSTx Table.
ifIndex - Each IEEE 802.11 interface is represented by an
ifEntry. Interface tables in this MIB module are indexed by ifIndex."
INDEX { ifIndex, dot11SupportedMCSTxIndex }
::= { dot11SupportedMCSTxTable 1 }
Dot11SupportedMCSTxEntry ::=
SEQUENCE {
dot11SupportedMCSTxIndex Unsigned32,
dot11SupportedMCSTxValue Unsigned32 }
dot11SupportedMCSTxIndex OBJECT-TYPE
SYNTAX Unsigned32 (1..255)
MAX-ACCESS not-accessible
STATUS current
DESCRIPTION
"Index object that identifies which MCS to access. Range is 1..255."
::= { dot11SupportedMCSTxEntry 1 }
dot11SupportedMCSTxValue OBJECT-TYPE
SYNTAX Unsigned32 (1..127)
MAX-ACCESS read-only
STATUS current
DESCRIPTION
"This is a capability variable.
Its value is determined by device capabilities.
The Transmit MCS supported by the PLCP and PMD, represented by a count
from 1 to 127, subject to limitations of each individual PHY."
::= { dot11SupportedMCSTxEntry 2 }
-- **********************************************************************
-- * End of dot11 Supported MCS Tx TABLE
-- **********************************************************************
-- **********************************************************************
-- * dot11 Supported MCS Rx TABLE
-- **********************************************************************
dot11SupportedMCSRxTable OBJECT-TYPE
SYNTAX SEQUENCE OF Dot11SupportedMCSRxEntry
MAX-ACCESS not-accessible
STATUS current
DESCRIPTION
"The receive MCS supported by the PLCP and PMD, represented by a count
from 1 to 127, subject to limitations of each individual PHY."
::= { dot11phy 17 }
dot11SupportedMCSRxEntry OBJECT-TYPE
SYNTAX Dot11SupportedMCSRxEntry
MAX-ACCESS not-accessible
STATUS current
DESCRIPTION
"An Entry (conceptual row) in the dot11SupportedMCSRx Table. ifIndex -
Each IEEE 802.11 interface is represented by an ifEntry. Interface tables
in this MIB module are indexed by ifIndex."
INDEX { ifIndex, dot11SupportedMCSRxIndex }
::= { dot11SupportedMCSRxTable 1 }
Dot11SupportedMCSRxEntry ::=
SEQUENCE {
dot11SupportedMCSRxIndex Unsigned32,
dot11SupportedMCSRxValue Unsigned32 }
dot11SupportedMCSRxIndex OBJECT-TYPE
SYNTAX Unsigned32 (1..255)
MAX-ACCESS not-accessible
STATUS current
DESCRIPTION
"Index object that identifies which MCS to access. Range is 1..255."
::= { dot11SupportedMCSRxEntry 1 }
dot11SupportedMCSRxValue OBJECT-TYPE
SYNTAX Unsigned32 (1..127)
MAX-ACCESS read-only
STATUS current
DESCRIPTION
"This is a capability variable.
Its value is determined by device capabilities.
The receive MCS supported by the PLCP and PMD, represented by a count from
1 to 127, subject to limitations of each individual PHY."
::= { dot11SupportedMCSRxEntry 2 }
-- **********************************************************************
-- * End of dot11 Supported MCS Rx TABLE
-- **********************************************************************
-- **********************************************************************
-- * dot11 Transmit Beamforming Config TABLE
-- **********************************************************************
dot11TransmitBeamformingConfigTable OBJECT-TYPE
SYNTAX SEQUENCE OF Dot11TransmitBeamformingConfigEntry
MAX-ACCESS not-accessible
STATUS current
DESCRIPTION
"Entry of attributes for dot11TransmitBeamformingConfigTable. Implemented
as a table indexed on ifIndex to allow for multiple instances on an
Agent."
::= { dot11phy 18 }
dot11TransmitBeamformingConfigEntry OBJECT-TYPE
SYNTAX Dot11TransmitBeamformingConfigEntry
MAX-ACCESS not-accessible
STATUS current
DESCRIPTION
"An entry in the dot11TransmitBeamformingConfig Table.
ifIndex - Each IEEE 802.11 interface is represented by an ifEntry. Interface
tables in this MIB module are indexed by ifIndex."
INDEX {ifIndex}
::= { dot11TransmitBeamformingConfigTable 1 }
Dot11TransmitBeamformingConfigEntry ::=
SEQUENCE {
dot11ReceiveStaggerSoundingOptionImplemented TruthValue,
dot11TransmitStaggerSoundingOptionImplemented TruthValue,
dot11ReceiveNDPOptionImplemented TruthValue,
dot11TransmitNDPOptionImplemented TruthValue,
dot11ImplicitTransmitBeamformingOptionImplemented TruthValue,
dot11CalibrationOptionImplemented INTEGER,
dot11ExplicitCSITransmitBeamformingOptionImplemented TruthValue,
dot11ExplicitNonCompressedBeamformingMatrixOptionImplemented
TruthValue,
dot11ExplicitTransmitBeamformingCSIFeedbackOptionImplemented
INTEGER,
dot11ExplicitNonCompressedBeamformingFeedbackOptionImplemented
INTEGER,
dot11ExplicitCompressedBeamformingFeedbackOptionImplemented
INTEGER,
dot11NumberBeamFormingCSISupportAntenna Unsigned32,
dot11NumberNonCompressedBeamformingMatrixSupportAntenna
Unsigned32,
dot11NumberCompressedBeamformingMatrixSupportAntenna Unsigned32 }
dot11ReceiveStaggerSoundingOptionImplemented OBJECT-TYPE
SYNTAX TruthValue
MAX-ACCESS read-only
STATUS current
DESCRIPTION
"This is a capability variable.
Its value is determined by device capabilities.
This attribute, when true, indicates that the STA implementation supports
the receiving of staggered sounding frames."
DEFVAL { false }
::= { dot11TransmitBeamformingConfigEntry 1 }
dot11TransmitStaggerSoundingOptionImplemented OBJECT-TYPE
SYNTAX TruthValue
MAX-ACCESS read-only
STATUS current
DESCRIPTION
"This is a capability variable.
Its value is determined by device capabilities.
This attribute, when true, indicates that the STA implementation supports
the transmission of staggered sounding frames."
DEFVAL { false }
::= { dot11TransmitBeamformingConfigEntry 2 }
dot11ReceiveNDPOptionImplemented OBJECT-TYPE
SYNTAX TruthValue
MAX-ACCESS read-only
STATUS current
DESCRIPTION
"This is a capability variable.
Its value is determined by device capabilities.
This attribute, when true, indicates that the STA implementation is capable
of receiving NDP as sounding frames."
DEFVAL { false }
::= { dot11TransmitBeamformingConfigEntry 3 }
dot11TransmitNDPOptionImplemented OBJECT-TYPE
SYNTAX TruthValue
MAX-ACCESS read-only
STATUS current
DESCRIPTION
"This is a capability variable.
Its value is determined by device capabilities.
This attribute, when true, indicates that the STA implementation is capable
of transmitting NDP as sounding frames."
DEFVAL { false }
::= { dot11TransmitBeamformingConfigEntry 4 }
dot11ImplicitTransmitBeamformingOptionImplemented OBJECT-TYPE
SYNTAX TruthValue
MAX-ACCESS read-only
STATUS current
DESCRIPTION
"This is a capability variable.
Its value is determined by device capabilities.
This attribute, when true, indicates that STA implementation is capable of
applying implicit transmit beamforming."
DEFVAL { false }
::= { dot11TransmitBeamformingConfigEntry 5 }
dot11CalibrationOptionImplemented OBJECT-TYPE
SYNTAX INTEGER {
inCapable (0),
unableToInitiate (1),
ableToInitiate (2),
fullyCapable (3) }
MAX-ACCESS read-only
STATUS current
DESCRIPTION
"This is a capability variable.
Its value is determined by device capabilities.
This attribute indicates the level of calibration supported by the STA
implementation."
DEFVAL { inCapable }
::= { dot11TransmitBeamformingConfigEntry 6 }
dot11ExplicitCSITransmitBeamformingOptionImplemented OBJECT-TYPE
SYNTAX TruthValue
MAX-ACCESS read-only
STATUS current
DESCRIPTION
"This is a capability variable.
Its value is determined by device capabilities.
This attribute, when true, indicates that STA implementation is capable of
applying transmit beamforming using CSI explicit feedback in its transmission."
DEFVAL { false }
::= { dot11TransmitBeamformingConfigEntry 7 }
dot11ExplicitNonCompressedBeamformingMatrixOptionImplemented OBJECT-TYPE
SYNTAX TruthValue
MAX-ACCESS read-only
STATUS current
DESCRIPTION
"This is a capability variable.
Its value is determined by device capabilities.
This attribute, when true, indicates that STA implementation is capable of
applying transmit beamforming using noncompressed beamforming feedback
matrix explicit feedback in its transmission."
DEFVAL { false }
::= { dot11TransmitBeamformingConfigEntry 8 }
dot11ExplicitTransmitBeamformingCSIFeedbackOptionImplemented OBJECT-TYPE
SYNTAX INTEGER {
inCapable (0),
delayed (1),
immediate (2),
unsolicitedImmediate (3),
aggregated (4),
delayedAggregated (5),
immediateAggregated(6),
unsolicitedImmediateAggregated (7) }
MAX-ACCESS read-only
STATUS current
DESCRIPTION
"This is a capability variable.
Its value is determined by device capabilities.
This attribute indicates the level of CSI explicit feedback returned by
the STA implementation."
DEFVAL { inCapable }
::= { dot11TransmitBeamformingConfigEntry 9 }
dot11ExplicitNonCompressedBeamformingFeedbackOptionImplemented OBJECT-TYPE
SYNTAX INTEGER {
inCapable (0),
delayed (1),
immediate (2),
unsolicitedImmediate (3),
aggregated (4),
delayedAggregated (5),
immediateAggregated(6),
unsolicitedImmediateAggregated (7) }
MAX-ACCESS read-only
STATUS current
DESCRIPTION
"This is a capability variable.
Its value is determined by device capabilities.
This attribute indicates the level of noncompressed beamforming feedback
matrix explicit feedback returned by the STA implementation."
DEFVAL { inCapable }
::= { dot11TransmitBeamformingConfigEntry 10 }
dot11ExplicitCompressedBeamformingFeedbackOptionImplemented OBJECT-TYPE
SYNTAX INTEGER {
inCapable (0),
delayed (1),
immediate (2),
unsolicitedImmediate (3),
aggregated (4),
delayedAggregated (5),
immediateAggregated(6),
unsolicitedImmediateAggregated (7) }
MAX-ACCESS read-only
STATUS current
DESCRIPTION
"This is a capability variable.
Its value is determined by device capabilities.
This attribute indicates the level of noncompressed beamforming feedback
matrix explicit feedback returned by the STA implementation."
DEFVAL { inCapable }
::= { dot11TransmitBeamformingConfigEntry 11 }
dot11NumberBeamFormingCSISupportAntenna OBJECT-TYPE
SYNTAX Unsigned32 (1..4)
MAX-ACCESS read-only
STATUS current
DESCRIPTION
"This is a capability variable.
Its value is determined by device capabilities.
This attribute indicates the maximum number of beamforming antennas the
beamformee can support when CSI feedback is required."
::= { dot11TransmitBeamformingConfigEntry 12 }
dot11NumberNonCompressedBeamformingMatrixSupportAntenna OBJECT-TYPE
SYNTAX Unsigned32 (1..4)
MAX-ACCESS read-only
STATUS current
DESCRIPTION
"This is a capability variable.
Its value is determined by device capabilities.
This attribute indicates the maximum number of beamforming antennas the
beamformee can support when noncompressed beamforming feedback matrix
feedback is required."
::= { dot11TransmitBeamformingConfigEntry 13 }
dot11NumberCompressedBeamformingMatrixSupportAntenna OBJECT-TYPE
SYNTAX Unsigned32 (1..4)
MAX-ACCESS read-only
STATUS current
DESCRIPTION
"This is a capability variable.
Its value is determined by device capabilities.
This attribute indicates the maximum number of beamforming antennas the
beamformee can support when compressed beamforming feedback matrix feedback
is required."
::= { dot11TransmitBeamformingConfigEntry 14 }
-- **********************************************************************
-- * End of dot11 Transmit Beamforming Config TABLE
-- **********************************************************************
-- **********************************************************************
-- * End of dot11PhyERP TABLE
-- **********************************************************************
-- Interworking Management (IMT) Attributes
-- DEFINED AS "The Interworking management object class provides
-- the necessary support for an SSPN Interface function to manage
-- interworking with external systems. IMT objects are conceptual
-- objects for Interworking Service and are defined only for the
-- AP."
dot11imt OBJECT IDENTIFIER ::= {ieee802dot11 6}
-- IMT GROUPS
-- dot11BSSIdTable ::= { dot11imt 1 }
-- dot11InterworkingTable ::= { dot11imt 2 }
-- dot11APLCI ::= { dot11imt 3 }
-- dot11APCivicLocation ::= { dot11imt 4 }
-- dot11RoamingConsortiumTable ::= { dot11imt 5 }
-- dot11DomainNameTable ::= { dot11imt 6 }
-- Generic Advertisement Service (GAS) Attributes
-- DEFINED AS "The Generic Advertisement Service management
-- object class provides the necessary support for an Advertisement
-- service to interwork with external systems."
-- GAS GROUPS
-- dot11GASAdvertisementTable ::= { dot11imt 7 }
--**********************************************************************
-- * dot11BSSId TABLE
--**********************************************************************
dot11BSSIdTable OBJECT-TYPE
SYNTAX SEQUENCE OF Dot11BSSIdEntry
MAX-ACCESS not-accessible
STATUS current
DESCRIPTION
"This object is a table of BSSIDs contained within an Access Point (AP)."
::= { dot11imt 1 }
dot11BSSIdEntry OBJECT-TYPE
SYNTAX Dot11BSSIdEntry
MAX-ACCESS not-accessible
STATUS current
DESCRIPTION
"This object provides the attributes identifying a particular BSSID within
an AP."
INDEX { dot11APMacAddress }
::= { dot11BSSIdTable 1 }
Dot11BSSIdEntry ::=
SEQUENCE{
dot11APMacAddress MacAddress
}
dot11APMacAddress OBJECT-TYPE
SYNTAX MacAddress
MAX-ACCESS read-only
STATUS current
DESCRIPTION
"This is a status variable.
Changes take effect for the next MLME-START.request primitive.
This object specifies the MAC address of the BSSID represented on a particular
BSSID interface and uniquely identifies this entry."
::= { dot11BSSIdEntry 1 }
--**********************************************************************
-- * End of dot11BSSId TABLE
--**********************************************************************
--**********************************************************************
-- * dot11Interworking TABLE
--**********************************************************************
dot11InterworkingTable OBJECT-TYPE
SYNTAX SEQUENCE OF Dot11InterworkingEntry
MAX-ACCESS not-accessible
STATUS current
DESCRIPTION
"This table represents the non-AP STAs associated to the AP. An entry is
created automatically by the AP when the STA becomes associated to the AP.
The corresponding entry is deleted when the STA disassociates. Each STA
added to this table is uniquely identified by its MAC address. This table
is moved to a new AP following a successful STA BSS transition event."
::= { dot11imt 2 }
dot11InterworkingEntry OBJECT-TYPE
SYNTAX Dot11InterworkingEntry
MAX-ACCESS not-accessible
STATUS current
DESCRIPTION
"Each entry represents a conceptual row in the dot11InterworkingTable and
provides information about permissions received from an SSPN Interface. If
a non-AP STA does not receive permissions for one or more of these
objects, then the object's default values or AP's locally defined configuration
may be used instead. If the AP's local policy(s) is more restrictive
than an object's value received from the SSPN Interface, then the
AP's local policy shall be enforced. An entry is identified by the AP's
MAC address to which the STA is associated and the STA's MAC address."
INDEX { dot11APMacAddress, dot11NonAPStationMacAddress }
::= { dot11InterworkingTable 1 }
Dot11InterworkingEntry ::=
SEQUENCE {
dot11NonAPStationMacAddress MacAddress,
dot11NonAPStationUserIdentity DisplayString,
dot11NonAPStationInterworkingCapability BITS,
dot11NonAPStationAssociatedSSID OCTET STRING,
dot11NonAPStationUnicastCipherSuite OCTET STRING,
dot11NonAPStationBroadcastCipherSuite OCTET STRING,
dot11NonAPStationAuthAccessCategories BITS,
dot11NonAPStationAuthMaxVoiceRate Unsigned32,
dot11NonAPStationAuthMaxVideoRate Unsigned32,
dot11NonAPStationAuthMaxBestEffortRate Unsigned32,
dot11NonAPStationAuthMaxBackgroundRate Unsigned32,
dot11NonAPStationAuthMaxVoiceOctets Unsigned32,
dot11NonAPStationAuthMaxVideoOctets Unsigned32,
dot11NonAPStationAuthMaxBestEffortOctets Unsigned32,
dot11NonAPStationAuthMaxBackgroundOctets Unsigned32,
dot11NonAPStationAuthMaxHCCAHEMMOctets Unsigned32,
dot11NonAPStationAuthMaxTotalOctets Unsigned32,
dot11NonAPStationAuthHCCAHEMM TruthValue,
dot11NonAPStationAuthMaxHCCAHEMMRate Unsigned32,
dot11NonAPStationAuthHCCAHEMMDelay Unsigned32,
dot11NonAPStationAuthSourceMulticast TruthValue,
dot11NonAPStationAuthMaxSourceMulticastRate Unsigned32,
dot11NonAPStationVoiceMSDUCount Counter32,
dot11NonAPStationDroppedVoiceMSDUCount Counter32,
dot11NonAPStationVoiceOctetCount Counter32,
dot11NonAPStationDroppedVoiceOctetCount Counter32,
dot11NonAPStationVideoMSDUCount Counter32,
dot11NonAPStationDroppedVideoMSDUCount Counter32,
dot11NonAPStationVideoOctetCount Counter32,
dot11NonAPStationDroppedVideoOctetCount Counter32,
dot11NonAPStationBestEffortMSDUCount Counter32,
dot11NonAPStationDroppedBestEffortMSDUCount Counter32,
dot11NonAPStationBestEffortOctetCount Counter32,
dot11NonAPStationDroppedBestEffortOctetCount Counter32,
dot11NonAPStationBackgroundMSDUCount Counter32,
dot11NonAPStationDroppedBackgroundMSDUCount Counter32,
dot11NonAPStationBackgroundOctetCount Counter32,
dot11NonAPStationDroppedBackgroundOctetCount Counter32,
dot11NonAPStationHCCAHEMMMSDUCount Counter32,
dot11NonAPStationDroppedHCCAHEMMMSDUCount Counter32,
dot11NonAPStationHCCAHEMMOctetCount Counter32,
dot11NonAPStationDroppedHCCAHEMMOctetCount Counter32,
dot11NonAPStationMulticastMSDUCount Counter32,
dot11NonAPStationDroppedMulticastMSDUCount Counter32,
dot11NonAPStationMulticastOctetCount Counter32,
dot11NonAPStationDroppedMulticastOctetCount Counter32,
dot11NonAPStationPowerManagementMode INTEGER,
dot11NonAPStationAuthDls TruthValue,
dot11NonAPStationVLANId Unsigned32,
dot11NonAPStationVLANName DisplayString,
dot11NonAPStationAddtsResultCode INTEGER}
dot11NonAPStationMacAddress OBJECT-TYPE
SYNTAX MacAddress
MAX-ACCESS read-only
STATUS current
DESCRIPTION
"This is a status variable.
It is written by the SME after a non-AP STA associates to the BSS.
This object specifies the MAC address of the non-AP STA for this entry and
uniquely identifies this entry."
::= { dot11InterworkingEntry 1 }
dot11NonAPStationUserIdentity OBJECT-TYPE
SYNTAX DisplayString (SIZE(0..255))
MAX-ACCESS read-only
STATUS current
DESCRIPTION
"This is a status variable.
It is written by the SME after a non-AP STA associates to the BSS.
This attribute reflects the user identity for the subscriber operating
this non-AP STA"
::= { dot11InterworkingEntry 2 }
dot11NonAPStationInterworkingCapability OBJECT-TYPE
SYNTAX BITS {
interworkingCapability(0),
qosMapCapability(1),
expeditedBwReqCapability(2),
msgcfCapability(3)
}
MAX-ACCESS read-only
STATUS current
DESCRIPTION
"This is a status variable.
It is written by the SME after a non-AP STA associates to the BSS.
This attribute defines the Interworking capabilities possessed by a non-AP
STA. Interworking Capability is set to 1 when the STA includes the Interworking
element in its (Re)Association request. The QosMapCapability,
ExpeditedBwReqCapability and MSGCFCapability bits reflect the same values
and meanings as those defined in 8.4.2.29"
::= { dot11InterworkingEntry 3 }
dot11NonAPStationAssociatedSSID OBJECT-TYPE
SYNTAX OCTET STRING (SIZE(0..32))
MAX-ACCESS read-only
STATUS current
DESCRIPTION
"This is a status variable.
It is written by the SME after a non-AP STA associates to the BSS.
This attribute reflects the SSID to which the non-AP STA is associated"
::= { dot11InterworkingEntry 4 }
dot11NonAPStationUnicastCipherSuite OBJECT-TYPE
SYNTAX OCTET STRING (SIZE(4))
MAX-ACCESS read-only
STATUS current
DESCRIPTION
"This is a status variable.
It is written by the SME after a non-AP STA authenticates with the BSS.
The selector of the AKM cipher suite that is currently in use by the non-
AP STA. It consists of an OUI (the first 3 octets) and a cipher suite
identifier (the last octet)."
::= { dot11InterworkingEntry 5 }
dot11NonAPStationBroadcastCipherSuite OBJECT-TYPE
SYNTAX OCTET STRING (SIZE(4))
MAX-ACCESS read-only
STATUS current
DESCRIPTION
"This is a status variable.
It is written by the SME after a non-AP STA authenticates with the BSS.
The selector of an AKM suite for broadcast and group addressed frame
transmissions. It consists of an OUI (the first 3 octets) and a cipher
suite identifier the last octet)."
::= { dot11InterworkingEntry 6 }
dot11NonAPStationAuthAccessCategories OBJECT-TYPE
SYNTAX BITS {
bestEffort(0),
background(1),
video(2),
voice(3)
}
MAX-ACCESS read-only
STATUS current
DESCRIPTION
"This is a control variable.
It is written by the SME after the AP receives the permissions for the
non-AP STA from the SSPN Interface.
The object that represents the access categories which the non-AP STA is
permitted to use when admission control is configured on that AC. An AC is
permitted to be used if its corresponding bit is set to 1; otherwise it is
not permitted to be used."
DEFVAL { { bestEffort, background, video, voice } }
::= { dot11InterworkingEntry 7 }
dot11NonAPStationAuthMaxVoiceRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s the non-
AP STA may use, either transmitting to an AP or receiving from an AP on
the voice access category. If this rate is exceeded, the AP should police
the flows traversing this AC. The value '4294967295', which is the default
value, means that the SSP is not requesting the AP to limit the data rate
used by the non-AP STA. Local configuration of the AP, however, may cause
the rate to be limited, especially when the AC is configured for mandatory
admission control."
DEFVAL {4294967295}
::= { dot11InterworkingEntry 8 }
dot11NonAPStationAuthMaxVideoRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s the non-
AP STA may use, either transmitting to an AP or receiving from an AP on
the video access category. If this rate is exceeded, the AP should police
the flows traversing this AC. The value '4294967295', which is the default
value, means that the SSP is not requesting the AP to limit the data rate
used by the non-AP STA. Local configuration of the AP, however, may cause
the rate to be limited, especially when the AC is configured for mandatory
admission control."
DEFVAL {4294967295}
::= { dot11InterworkingEntry 9 }
dot11NonAPStationAuthMaxBestEffortRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s the non-
AP STA may use, either transmitting to an AP or receiving from an AP on
the best effort access category. If this rate is exceeded, the AP should
police the flows traversing this AC. The value '4294967295', which is the
default value, means that the SSP is not requesting the AP to limit the
data rate used by the non-AP STA. Local configuration of the AP, however,
may cause the rate to be limited, especially when the AC is configured for
mandatory admission control."
DEFVAL {4294967295}
::= { dot11InterworkingEntry 10 }
dot11NonAPStationAuthMaxBackgroundRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s the non-
AP STA may use, either transmitting to an AP or receiving from an AP on
the background access category. If this rate is exceeded, the AP should
police the flows traversing this AC. The value '4294967295', which is the
default value, means that the SSP is not requesting the AP to limit the
data rate used by the non-AP STA. Local configuration of the AP, however,
may cause the rate to be limited, especially when the AC is configured for
mandatory admission control."
DEFVAL {4294967295}
::= { dot11InterworkingEntry 11 }
dot11NonAPStationAuthMaxVoiceOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use on the voice access category. If this octet count is exceeded,
the AP should disassociate the non-AP STA. A value of 0 indicates that
there is no octet limit."
DEFVAL {0}
::= { dot11InterworkingEntry 12 }
dot11NonAPStationAuthMaxVideoOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use on the video access category. If this octet count is exceeded,
the AP should disassociate the non-AP STA. A value of 0 indicates that
there is no octet limit."
DEFVAL {0}
::= { dot11InterworkingEntry 13 }
dot11NonAPStationAuthMaxBestEffortOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use on the best effort access category. If this octet count is
exceeded, the AP should disassociate the non-AP STA. A value of 0 indicates
that there is no octet limit."
DEFVAL {0}
::= { dot11InterworkingEntry 14 }
dot11NonAPStationAuthMaxBackgroundOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use on the background access category. If this octet count is
exceeded, the AP should disassociate the non-AP STA. A value of 0 indicates
that there is no octet limit."
DEFVAL {0}
::= { dot11InterworkingEntry 15 }
dot11NonAPStationAuthMaxHCCAHEMMOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use with HCCA or HEMM access. If this octet count is exceeded, the
AP should disassociate the non-AP STA. A value of 0 indicates that there
is no octet limit."
DEFVAL {0}
::= { dot11InterworkingEntry 16 }
dot11NonAPStationAuthMaxTotalOctets OBJECT-TYPE
SYNTAX Unsigned32 (0..4294967295)
MAX-ACCESS read-only
STATUS current
DESCRIPTION
"This is a control variable.
It is written by the SME after the AP receives the permissions for the
non-AP STA from the SSPN Interface.
This attribute indicates the maximum authorized total octet count that a
STA may use on all access categories combined. If this octet count is
exceeded, the AP should disassociate the non-AP STA. A value of 0 indicates
that there is no octet limit."
DEFVAL {0}
::= { dot11InterworkingEntry 17 }
dot11NonAPStationAuthHCCAHEMM OBJECT-TYPE
SYNTAX TruthValue
MAX-ACCESS read-only
STATUS current
DESCRIPTION
"This is a control variable.
It is written by the SME after the AP receives the permissions for the
non-AP STA from the SSPN Interface.
This attribute, when true, indicates that the non-AP STA is permitted by
the SSP to request HCCA or HEMM service via ADDTS management frames. If
this attribute is false, then HCCA or HEMM service is not permitted by the
SSP."
DEFVAL {true}
::= { dot11InterworkingEntry 18 }
dot11NonAPStationAuthMaxHCCAHEMMRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s the non-
AP STA may use, either transmitting to an AP or receiving from an AP via
HCCA or HEMM. The value '4294967295', which is the default value, means
that the SSP is not requesting the AP to limit the data rate used by the
non-AP STA. Local configuration of the AP, however, may cause the rate to
be otherwise limited."
DEFVAL {4294967295}
::= { dot11InterworkingEntry 19 }
dot11NonAPStationAuthHCCAHEMMDelay OBJECT-TYPE
SYNTAX Unsigned32 (1..4294967295)
UNITS "microseconds"
MAX-ACCESS read-only
STATUS current
DESCRIPTION
"This is a control variable.
It is written by the SME after the AP receives the permissions for the
non-AP STA from the SSPN Interface.
This attribute indicates the delay bound for frames queued at an AP to a
non-AP STA in the HCCA or HEMM queue. An AP should deliver frames to the
non-AP STA within the time period specified in this attribute. When a non-
AP STA requests admission control to the HCCA or HEMM queue, the requested
delay will be equal to or higher than this value. The value '4294967295',
which is the default value, means that the SSP is not requesting the AP
limit the delay bound in this queue for transmissions to the non-AP STA."
DEFVAL {4294967295}
::= { dot11InterworkingEntry 20 }
dot11NonAPStationAuthSourceMulticast OBJECT-TYPE
SYNTAX TruthValue
MAX-ACCESS read-only
STATUS current
DESCRIPTION
"This is a control variable.
It is written by the SME after the AP receives the permissions for the
non-AP STA from the SSPN Interface.
This attribute, when true, indicates that the AP.s MAC sublayer shall perform
rate limiting to enforce the resource utilization limit in
dot11NonAPStationAuthMaxSourceMulticastRate in the dot11InterworkingEntry
identified by the source MAC address of the received frame. If this attribute
is false, at an AP for which dot11SSPNInterfaceActivated is true,
upon receipt of a frame of type data with group DA, then the AP.s MAC sublayer
shall discard the frame."
DEFVAL {true}
::= { dot11InterworkingEntry 21 }
dot11NonAPStationAuthMaxSourceMulticastRate OBJECT-TYPE
SYNTAX Unsigned32 (1..4294967295)
UNITS "kb/s"
MAX-ACCESS read-only
STATUS current
DESCRIPTION
"This is a control variable.
It is written by the SME after the AP receives the permissions for the
non-AP STA from the SSPN Interface.
This attribute indicates the maximum authorized data rate in kb/s which
the non-AP STA may transmit group addressed frames to an AP. If this rate
is exceeded, the AP should police the flows. The value '4294967295', which
is the default value, means that the SSP is not requesting the AP to limit
the multicast data rate used by the non-AP STA."
DEFVAL {4294967295}
::= { dot11InterworkingEntry 22 }
dot11NonAPStationVoiceMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU successfully
transmitted by the AP on the voice access category and for each
MSDU successfully received on either user priority 6 or 7."
::= { dot11InterworkingEntry 23 }
dot11NonAPStationDroppedVoiceMSDUCount OBJECT-TYPE
SYNTAX Counter32
MAX-ACCESS read-only
STATUS current
DESCRIPTION
"This is a status variable.
It is written by the AP.s MAC after the completion of an MA-UNITDATA.confirm 
or MA-UNITDATA.indication primitive.
For EDCA operation, this counter shall be incremented for each MSDU
dropped by the AP on the voice access category."
::= { dot11InterworkingEntry 24 }
dot11NonAPStationVoiceOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented by the octet length
of each MSDU successfully transmitted by the AP on the voice access category
and by the octet length of each MSDU successfully received on either
user priority 6 or 7."
::= { dot11InterworkingEntry 25 }
dot11NonAPStationDroppedVoiceOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each octet
dropped by the AP on the voice access category."
::= { dot11InterworkingEntry 26 }
dot11NonAPStationVideoMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU successfully
transmitted by the AP on the video access category and for each
MSDU successfully received on either user priority 4 or 5."
::= { dot11InterworkingEntry 27 }
dot11NonAPStationDroppedVideoMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU
dropped by the AP on the video access category."
::= { dot11InterworkingEntry 28 }
dot11NonAPStationVideoOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented by the octet length
of each MSDU successfully transmitted by the AP on the voice access category
and by the octet length of each MSDU successfully received on either
user priority 4 or 5."
::= { dot11InterworkingEntry 29 }
dot11NonAPStationDroppedVideoOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each octet
dropped by the AP on the video access category."
::= { dot11InterworkingEntry 30 }
dot11NonAPStationBestEffortMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU successfully
transmitted by the AP on the best effort access category and for
each MSDU successfully received on either user priority 0 or 3. For DCF or
PCF operation, this counter shall be incremented for each MSDU successfully
transmitted or received by the AP."
::= { dot11InterworkingEntry 31 }
dot11NonAPStationDroppedBestEffortMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU
dropped by the AP on the best effort access category and for each MSDU
dropped by the AP on either user priority 0 or 3. For DCF or PCF operation,
this counter shall be incremented for each MSDU dropped by the AP."
::= { dot11InterworkingEntry 32 }
dot11NonAPStationBestEffortOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented by the octet length
of each MSDU successfully transmitted by the AP on the best effort access
category and by the octet length of each MSDU successfully received on
either user priority 0 or 3. For DCF or PCF operation, this counter shall
be incremented the octet length of each MSDU successfully transmitted or
received by the AP."
::= { dot11InterworkingEntry 33 }
dot11NonAPStationDroppedBestEffortOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for the octet length
of each MSDU dropped by the AP on the best effort access category and by
the octet length of each MSDU dropped by the AP for either user priority 0
or 3. For DCF or PCF operation, this counter shall be incremented for the
octet length of each MSDU dropped by the AP."
::= { dot11InterworkingEntry 34 }
dot11NonAPStationBackgroundMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU successfully
transmitted by the AP on the background access category and for
each MSDU successfully received on either user priority 1 or 2."
::= { dot11InterworkingEntry 35 }
dot11NonAPStationDroppedBackgroundMSDUCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented for each MSDU
dropped by the AP on the background access category"
::= { dot11InterworkingEntry 36 }
dot11NonAPStationBackgroundOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented by the octet length
of each MSDU successfully transmitted by the AP on the background access
category and by the octet length of each MSDU successfully received on
either user priority 1 or 2."
::= { dot11InterworkingEntry 37 }
dot11NonAPStationDroppedBackgroundOctetCount OBJECT-TYPE
SYNTAX Counter32
MAX-ACCESS read-only
STATUS current
DESCRIPTION
"This is a status variable.
It is written by the AP.s MAC after the completion of an MA-UNITDATA.confirm
or MA-UNITDATA.indication primitive.
For EDCA operation, this counter shall be incremented by the octet length
of each MSDU dropped by the AP on the background access category"
::= { dot11InterworkingEntry 38 }
dot11NonAPStationHCCAHEMMMSDUCount OBJECT-TYPE
SYNTAX Counter32
MAX-ACCESS read-only
STATUS current
DESCRIPTION
"This is a status variable.
It is written by the AP.s MAC after the completion of an MA-UNITDATA.confirm
or MA-UNITDATA.indication primitive.
For HCCA or HEMM operation, this counter shall be incremented for each
MSDU successfully transmitted by the AP and for each MSDU successfully
received on either."
::= { dot11InterworkingEntry 39 }
dot11NonAPStationDroppedHCCAHEMMMSDUCount OBJECT-TYPE
SYNTAX Counter32
MAX-ACCESS read-only
STATUS current
DESCRIPTION
"This is a status variable.
It is written by the AP.s MAC after the completion of an MA-UNITDATA.confirm
or MA-UNITDATA.indication primitive.
For HCCA or HEMM operation, this counter shall be incremented for each
MSDU dropped by the AP."
::= { dot11InterworkingEntry 40 }
dot11NonAPStationHCCAHEMMOctetCount OBJECT-TYPE
SYNTAX Counter32
MAX-ACCESS read-only
STATUS current
DESCRIPTION
"This is a status variable.
It is written by the AP.s MAC after the completion of an MA-UNITDATA.confirm
or MA-UNITDATA.indication primitive.
For HCCA or HEMM operation, this counter shall be incremented by the octet
length of each MSDU successfully transmitted by the AP and by the octet
length of each MSDU successfully received."
::= { dot11InterworkingEntry 41 }
dot11NonAPStationDroppedHCCAHEMMOctetCount OBJECT-TYPE
SYNTAX Counter32
MAX-ACCESS read-only
STATUS current
DESCRIPTION
"This is a status variable.
It is written by the AP.s MAC after the completion of an MA-UNITDATA.confirm
or MA-UNITDATA.indication primitive.
For HCCA or HEMM operation, this counter shall be incremented by the octet
length of each MSDU dropped by the AP."
::= { dot11InterworkingEntry 42 }
dot11NonAPStationMulticastMSDUCount OBJECT-TYPE
SYNTAX Counter32
MAX-ACCESS read-only
STATUS current
DESCRIPTION
"This is a status variable.
It is written by the AP.s MAC after the completion of an MA-UNITDATA.confirm
or MA-UNITDATA.indication primitive.
For Multicast operation, this counter shall be incremented for each Multicast
MSDU successfully transmitted by the AP and for each Multicast MSDU
successfully received at the AP."
::= { dot11InterworkingEntry 43 }
dot11NonAPStationDroppedMulticastMSDUCount OBJECT-TYPE
SYNTAX Counter32
MAX-ACCESS read-only
STATUS current
DESCRIPTION
"This is a status variable.
It is written by the AP.s MAC after the completion of an MA-UNITDATA.confirm
or MA-UNITDATA.indication primitive.
For Multicast operation, this counter shall be incremented for each Multicast
MSDU dropped by the AP."
::= { dot11InterworkingEntry 44 }
dot11NonAPStationMulticastOctetCount OBJECT-TYPE
SYNTAX Counter32
MAX-ACCESS read-only
STATUS current
DESCRIPTION
"This is a status variable.
It is written by the AP.s MAC after the completion of an MA-UNITDATA.confirm
or MA-UNITDATA.indication primitive.
For Multicast operation, this counter shall be incremented by the octet
length of each MSDU successfully transmitted by the AP and by the octet
length of each Multicast MSDU successfully received."
::= { dot11InterworkingEntry 45 }
dot11NonAPStationDroppedMulticastOctetCount OBJECT-TYPE
SYNTAX Counter32
MAX-ACCESS read-only
STATUS current
DESCRIPTION
"This is a status variable.
It is written by the AP.s MAC after the completion of an MA-UNITDATA.confirm
or MA-UNITDATA.indication primitive.
For Multicast operation, this counter shall be incremented by the octet
length of each Multicast MSDU dropped by the AP."
::= { dot11InterworkingEntry 46 }
dot11NonAPStationPowerManagementMode OBJECT-TYPE
SYNTAX INTEGER { active(1), powersave(2) }
MAX-ACCESS read-only
STATUS current
DESCRIPTION
"This is a status variable.
It is written by the AP.s MAC after the non-AP STA changes it.s power management
mode.
This attribute indicates the power management mode of the non-AP STA."
::= { dot11InterworkingEntry 47 }
dot11NonAPStationAuthDls OBJECT-TYPE
SYNTAX TruthValue
MAX-ACCESS read-only
STATUS current
DESCRIPTION
"This is a control variable.
It is written by the SME after the AP receives the permissions for the
non-AP STA from the SSPN Interface.
This attribute, when true, indicates that the non-AP STA is permitted by
the SSPN Interface to use direct link service (DLS). Note this attribute
is an SSP permission and is independent of whether DLS is allowed in the
BSS as governed by dot11DLSAllowedInQBSS. This service is disabled otherwise."
DEFVAL {true}
::= { dot11InterworkingEntry 48 }
dot11NonAPStationVLANId OBJECT-TYPE
SYNTAX Unsigned32 (0..4095)
MAX-ACCESS read-only
STATUS current
DESCRIPTION
"This is a status variable.
It is written by the SME after a non-AP STA associates to the BSS.
This attribute indicates the VLAN ID on the an external network to which
frames from the non-AP STA are bridged."
::= { dot11InterworkingEntry 49 }
dot11NonAPStationVLANName OBJECT-TYPE
SYNTAX DisplayString (SIZE(0..64))
MAX-ACCESS read-only
STATUS current
DESCRIPTION
"This is a status variable.
It is written by the SME after a non-AP STA associates to the BSS.
This attribute indicates the VLAN name corresponding to the VLAN ID on the
external network to which frames from the non-AP STA are bridged."
::= { dot11InterworkingEntry 50 }
dot11NonAPStationAddtsResultCode OBJECT-TYPE
SYNTAX INTEGER {
success(1),
invalidParameters(2),
rejectedWithSuggestedChanges(3),
rejectedForDelayPeriod(4),
rejectedForSspPermissions(5),
rejectedWithSuggestedBssTransition (6),
requestedTclasNotSupported (7),
tclasResourcesExhausted (8),
rejectedHomeWithSuggestedChanges (9)
}
MAX-ACCESS read-only
STATUS current
DESCRIPTION
"This is a status variable.
It is written by the AP.s HC after the AP transmits an ADDTS Response to
the non-AP STA or after the AP includes a RIC element in a Reassociation
Response frame.
This attribute indicates the most recent result code returned by the AP in
an ADDTS Response."
::= { dot11InterworkingEntry 51 }
-- **********************************************************************
-- * End of dot11Interworking TABLE
-- **********************************************************************
-- **********************************************************************
-- * dot11APLCI TABLE
-- **********************************************************************
dot11APLCITable OBJECT-TYPE
SYNTAX SEQUENCE OF Dot11APLCIEntry
MAX-ACCESS not-accessible
STATUS current
DESCRIPTION
"This table represents the Geospatial location of the AP as specified in
8.4.2.23.10."
::= { dot11imt 3 }
dot11APLCIEntry OBJECT-TYPE
SYNTAX Dot11APLCIEntry
MAX-ACCESS not-accessible
STATUS current
DESCRIPTION
"AP location in Geospatial coordinates"
INDEX { dot11APLCIIndex }
::= { dot11APLCITable 1 }
Dot11APLCIEntry ::=
SEQUENCE {
dot11APLCIIndex Unsigned32,
dot11APLCILatitudeResolution Unsigned32,
dot11APLCILatitudeInteger Integer32,
dot11APLCILatitudeFraction Integer32,
dot11APLCILongitudeResolution Unsigned32,
dot11APLCILongitudeInteger Integer32,
dot11APLCILongitudeFraction Integer32,
dot11APLCIAltitudeType INTEGER,
dot11APLCIAltitudeResolution Unsigned32,
dot11APLCIAltitudeInteger Integer32,
dot11APLCIAltitudeFraction Integer32,
dot11APLCIDatum INTEGER,
dot11APLCIAzimuthType INTEGER,
dot11APLCIAzimuthResolution Unsigned32,
dot11APLCIAzimuth Integer32
}
dot11APLCIIndex OBJECT-TYPE
SYNTAX Unsigned32
MAX-ACCESS not-accessible
STATUS current
DESCRIPTION
"Index for AP LCI elements in dot11APLCITable, greater than 0."
::= { dot11APLCIEntry 1 }
dot11APLCILatitudeResolution OBJECT-TYPE
SYNTAX Unsigned32 (0..63)
MAX-ACCESS read-write
STATUS current
DESCRIPTION
"This is a control variable.
It is written by an external management entity or the SME.
Changes take effect as soon as practical in the implementation.
Latitude resolution is 6 bits indicating the number of valid bits in the
fixed-point value of Latitude. This field is derived from IETF RFC 3825."
::= { dot11APLCIEntry 2 }
dot11APLCILatitudeInteger OBJECT-TYPE
SYNTAX Integer32 (-90..90)
MAX-ACCESS read-write
STATUS current
DESCRIPTION
"This is a control variable.
It is written by an external management entity or the SME.
Changes take effect as soon as practical in the implementation.
Latitude is a 34 bit fixed point value consisting of 9 bits of integer and
25 bits of fraction. This field contains the 9 bits of integer portion of
Latitude. This field is derived from IETF RFC 3825."
::= { dot11APLCIEntry 3 }
dot11APLCILatitudeFraction OBJECT-TYPE
SYNTAX Integer32 (-16777215..16777215)
MAX-ACCESS read-write
STATUS current
DESCRIPTION
"This is a control variable.
It is written by an external management entity or the SME.
Changes take effect as soon as practical in the implementation.
Latitude is a 34 bit fixed point value consisting of 9 bits of integer and
25 bits of fraction. This field contains the 25 bits of fraction portion
of Latitude. This field is derived from IETF RFC 3825."
::= { dot11APLCIEntry 4 }
dot11APLCILongitudeResolution OBJECT-TYPE
SYNTAX Unsigned32 (0..63)
MAX-ACCESS read-write
STATUS current
DESCRIPTION
"This is a control variable.
It is written by an external management entity or the SME.
Changes take effect as soon as practical in the implementation.
Longitude resolution is 6 bits indicating the number of valid bits in the
fixed-point value of Longitude. This field is derived from IETF RFC 3825."
::= { dot11APLCIEntry 5 }
dot11APLCILongitudeInteger OBJECT-TYPE
SYNTAX Integer32 (-180..180)
MAX-ACCESS read-write
STATUS current
DESCRIPTION
"This is a control variable.
It is written by an external management entity or the SME.
Changes take effect as soon as practical in the implementation.
Longitude is a 34 bit fixed point value consisting of 9 bits of integer
and 25 bits of fraction. This field contains the 9 bits of integer portion
of Longitude. This field is derived from IETF RFC 3825."
::= { dot11APLCIEntry 6 }
dot11APLCILongitudeFraction OBJECT-TYPE
SYNTAX Integer32 (-16777215..16777215)
MAX-ACCESS read-write
STATUS current
DESCRIPTION
"This is a control variable.
It is written by an external management entity or the SME.
Changes take effect as soon as practical in the implementation.
Longitude is a twos complement 34 bit fixed point value consisting of 9
bits of integer and 25 bits of fraction. This field contains the 25 bits
of fraction portion of Longitude. This field is derived from IETF RFC
3825."
::= { dot11APLCIEntry 7 }
dot11APLCIAltitudeType OBJECT-TYPE
SYNTAX INTEGER {
meters(1),
floors(2),
hagm (3) }
MAX-ACCESS read-write
STATUS current
DESCRIPTION
"This is a control variable.
It is written by an external management entity or the SME.
Changes take effect as soon as practical in the implementation.
Altitude Type is four bits encoding the type of altitude. Codes defined
are: meters in 2s-complement fixed-point 22-bit integer part with 8-bit
fraction floors in 2s-complement fixed-point 22-bit integer part with 8-
bit fraction hagm: Height Above Ground in meters, in 2s-complement fixedpoint
22-bit integer part with 8-bit fraction. This field is derived from
IETF RFC 3825."
::= { dot11APLCIEntry 8 }
dot11APLCIAltitudeResolution OBJECT-TYPE
SYNTAX Unsigned32 (0..63)
MAX-ACCESS read-write
STATUS current
DESCRIPTION
"This is a control variable.
It is written by an external management entity or the SME.
Changes take effect as soon as practical in the implementation.
Altitude resolution is 6 bits indicating the number of valid bits in the
altitude. This field is derived from IETF RFC 3825."
::= { dot11APLCIEntry 9 }
dot11APLCIAltitudeInteger OBJECT-TYPE
SYNTAX Integer32 (-2097151..2097151)
MAX-ACCESS read-write
STATUS current
DESCRIPTION
"This is a control variable.
It is written by an external management entity or the SME.
Changes take effect as soon as practical in the implementation.
Altitude is a 30 bit value defined by the Altitude type field. The field
is encoded as a 2s-complement fixed-point 22-bit integer Part with 8-bit
fraction. This field contains the fixed-point Part of Altitude. This field
is derived from IETF RFC 3825."
::= { dot11APLCIEntry 10 }
dot11APLCIAltitudeFraction OBJECT-TYPE
SYNTAX Integer32 (-127..127)
MAX-ACCESS read-write
STATUS current
DESCRIPTION
"This is a control variable.
It is written by an external management entity or the SME.
Changes take effect as soon as practical in the implementation.
Altitude is a 30 bit value defined by the Altitude type field. The field
is encoded as a 2s-complement fixed-point 22-bit integer Part with 8-bit
fraction. This field is derived from IETF RFC 3825."
::= { dot11APLCIEntry 11 }
dot11APLCIDatum OBJECT-TYPE
SYNTAX INTEGER {
wgs84 (1),
nad83navd88 (2),
nad93mllwvd (3)
}
MAX-ACCESS read-write
STATUS current
DESCRIPTION
"This is a control variable.
It is written by an external management entity or the SME.
Changes take effect as soon as practical in the implementation.
Datum is an 8-bit value encoding the horizontal and vertical references
used for the coordinates given in this LCI. IETF RFC 3825 defines the values
of Datum. Type 1 is WGS-84, the coordinate system used by GPS. Type 2
is NAD83 with NAVD88 vertical reference. Type 3 is NAD83 with Mean Lower
Low Water vertical datum. All other types are reserved. This field is
derived from IETF RFC 3825."
::= { dot11APLCIEntry 12 }
dot11APLCIAzimuthType OBJECT-TYPE
SYNTAX INTEGER {
frontSurfaceOfSTA(0),
radioBeam(1) }
MAX-ACCESS read-write
STATUS current
DESCRIPTION
"This is a control variable.
It is written by an external management entity or the SME.
Changes take effect as soon as practical in the implementation.
Azimuth Type is a one bit attribute encoding the type of Azimuth. Codes
defined are: front surface of STA: in 2s-complement fixed-point 9-bit
integer radio beam: in 2s-complement fixed-point 9-bit integer."
::= { dot11APLCIEntry 13 }
dot11APLCIAzimuthResolution OBJECT-TYPE
SYNTAX Unsigned32 (0..15)
MAX-ACCESS read-write
STATUS current
DESCRIPTION
"This is a control variable.
It is written by an external management entity or the SME.
Changes take effect as soon as practical in the implementation.
Azimuth Resolution is 4 bits indicating the number of valid bits in the
azimuth."
::= { dot11APLCIEntry 14 }
dot11APLCIAzimuth OBJECT-TYPE
SYNTAX Integer32 (-511..511)
MAX-ACCESS read-write
STATUS current
DESCRIPTION
"This is a control variable.
It is written by an external management entity or the SME.
Changes take effect as soon as practical in the implementation.
Azimuth is a 9 bit value defined by the Azimuth Type field.The field is
encoded as a 2s-complement fixed-point 9-bit integer horizontal angle in
degrees from true north."
::= { dot11APLCIEntry 15 }
-- **********************************************************************
-- * End of dot11APLCI TABLE
-- **********************************************************************
-- **********************************************************************
-- * dot11APCivicLocation TABLE
-- **********************************************************************
dot11APCivicLocationTable OBJECT-TYPE
SYNTAX SEQUENCE OF Dot11ApCivicLocationEntry
MAX-ACCESS not-accessible
STATUS current
DESCRIPTION
"This table represents the location of the AP in Civic format using the
Civic Address Type elements defined in IETF RFC-5139 [B42]."
::= { dot11imt 4 }
dot11APCivicLocationEntry OBJECT-TYPE
SYNTAX Dot11ApCivicLocationEntry
MAX-ACCESS not-accessible
STATUS current
DESCRIPTION
"Civic Address location of the AP described with Civic Address Type elements
defined in IETF RFC-5139 [B42]."
INDEX {dot11APCivicLocationIndex} ::= {dot11APCivicLocationTable 1}
Dot11ApCivicLocationEntry ::=
SEQUENCE {
dot11APCivicLocationIndex Unsigned32,
dot11APCivicLocationCountry OCTET STRING,
dot11APCivicLocationA1 OCTET STRING,
dot11APCivicLocationA2 OCTET STRING,
dot11APCivicLocationA3 OCTET STRING,
dot11APCivicLocationA4 OCTET STRING,
dot11APCivicLocationA5 OCTET STRING,
dot11APCivicLocationA6 OCTET STRING,
dot11APCivicLocationPrd OCTET STRING,
dot11APCivicLocationPod OCTET STRING,
dot11APCivicLocationSts OCTET STRING,
dot11APCivicLocationHno OCTET STRING,
dot11APCivicLocationHns OCTET STRING,
dot11APCivicLocationLmk OCTET STRING,
dot11APCivicLocationLoc OCTET STRING,
dot11APCivicLocationNam OCTET STRING,
dot11APCivicLocationPc OCTET STRING,
dot11APCivicLocationBld OCTET STRING,
dot11APCivicLocationUnit OCTET STRING,
dot11APCivicLocationFlr OCTET STRING,
dot11APCivicLocationRoom OCTET STRING,
dot11APCivicLocationPlc OCTET STRING,
dot11APCivicLocationPcn OCTET STRING,
dot11APCivicLocationPobox OCTET STRING,
dot11APCivicLocationAddcode OCTET STRING,
dot11APCivicLocationSeat OCTET STRING,
dot11APCivicLocationRd OCTET STRING,
dot11APCivicLocationRdsec OCTET STRING,
dot11APCivicLocationRdbr OCTET STRING,
dot11APCivicLocationRdsubbr OCTET STRING,
dot11APCivicLocationPrm OCTET STRING,
dot11APCivicLocationPom OCTET STRING
}
dot11APCivicLocationIndex OBJECT-TYPE
SYNTAX Unsigned32
MAX-ACCESS not-accessible
STATUS current
DESCRIPTION
"This is a control variable.
It is written by an external management entity or the SME.
Changes take effect as soon as practical in the implementation.
Index for APCivicLocation elements in dot11APCivicLocationTable, greater
than 0."
::= { dot11APCivicLocationEntry 1 }
dot11APCivicLocationCountry OBJECT-TYPE
SYNTAX OCTET STRING (SIZE(0..255))
MAX-ACCESS read-write
STATUS current
DESCRIPTION
"This is a control variable.
It is written by an external management entity or the SME.
Changes take effect as soon as practical in the implementation.
This attribute contains the two uppercase characters which correspond to
the alpha-2 codes in ISO 3166-1. Example: US."
::= { dot11APCivicLocationEntry 2 }
dot11APCivicLocationA1 OBJECT-TYPE
SYNTAX OCTET STRING (SIZE(0..255))
MAX-ACCESS read-write
STATUS current
DESCRIPTION
"This is a control variable.
It is written by an external management entity or the SME.
Changes take effect as soon as practical in the implementation.
This attribute contains the national subdivisions (state, Region, province,
prefecture). Example: California. The A1 element is used for the top
level subdivision within a country. In the absence of a country-specific
guide on how to use the A-series of elements, the second part of the ISO
3166-2 code [ISO.3166-2] for a country subdivision SHOULD be used. The ISO
3166-2 code is a formed of a country code and hyphen plus a code of one,
two or three characters or numerals. For the A1 element, the leading country
code and hyphen are omitted and only the subdivision code is included.
For example, the codes for Canada include CA-BC, CA-ON, CA-QC;Luxembourg
has just three single character codes: LU-D, LU-G And LU-L; Australia uses
both two and three character codes: AU-ACT, AU-NSW, AU-NT; France uses
numerical codes for mainland France and letters for territories: FR-75,
FR-NC."
::= { dot11APCivicLocationEntry 3 }
dot11APCivicLocationA2 OBJECT-TYPE
SYNTAX OCTET STRING (SIZE(0..255))
MAX-ACCESS read-write
STATUS current
DESCRIPTION
"This is a control variable.
It is written by an external management entity or the SME.
Changes take effect as soon as practical in the implementation.
This attribute contains the county, parish, gun (JP), district (IN). Example:
King.s County."
::= { dot11APCivicLocationEntry 4 }
dot11APCivicLocationA3 OBJECT-TYPE
SYNTAX OCTET STRING (SIZE(0..255))
MAX-ACCESS read-write
STATUS current
DESCRIPTION
"This is a control variable.
It is written by an external management entity or the SME.
Changes take effect as soon as practical in the implementation.
This attribute contains the city, township, shi (JP). Example: San Francisco."
::= { dot11APCivicLocationEntry 5 }
dot11APCivicLocationA4 OBJECT-TYPE
SYNTAX OCTET STRING (SIZE(0..255))
MAX-ACCESS read-write
STATUS current
DESCRIPTION
"This is a control variable.
It is written by an external management entity or the SME.
Changes take effect as soon as practical in the implementation.
This attribute contains the city division, borough, city district, ward,
chou (JP). Example: Manhattan."
::= { dot11APCivicLocationEntry 6 }
dot11APCivicLocationA5 OBJECT-TYPE
SYNTAX OCTET STRING (SIZE(0..255))
MAX-ACCESS read-write
STATUS current
DESCRIPTION
"This is a control variable.
It is written by an external management entity or the SME.
Changes take effect as soon as practical in the implementation.
This attribute contains the neighborhood, block. Example: Morningside
Heights."
::= { dot11APCivicLocationEntry 7 }
dot11APCivicLocationA6 OBJECT-TYPE
SYNTAX OCTET STRING (SIZE(0..255))
MAX-ACCESS read-write
STATUS current
DESCRIPTION
"This is a control variable.
It is written by an external management entity or the SME.
Changes take effect as soon as practical in the implementation.
This attribute contains the street. Example: Broadway. The A6 element is
retained for use in those countries that require this level of detail.
Where A6 was previously used for street names in IETF RFC 5139 [B42], it
will not be used, the RD element will be used for thorough fare data. However,
without additional information these fields will not be interchanged
when converting between different Civic formats. Where Civic address
information is obtained from another format, such as the DHCP form IETF
RFC 4776 [B40], the A6 element will be copied directly from the source
format."
::= { dot11APCivicLocationEntry 8 }
dot11APCivicLocationPrd OBJECT-TYPE
SYNTAX OCTET STRING (SIZE(0..255))
MAX-ACCESS read-write
STATUS current
DESCRIPTION
"This is a control variable.
It is written by an external management entity or the SME.
Changes take effect as soon as practical in the implementation.
This attribute contains the leading street direction. Example: NW."
::= { dot11APCivicLocationEntry 9 }
dot11APCivicLocationPod OBJECT-TYPE
SYNTAX OCTET STRING (SIZE(0..255))
MAX-ACCESS read-write
STATUS current
DESCRIPTION
"This is a control variable.
It is written by an external management entity or the SME.
Changes take effect as soon as practical in the implementation.
This attribute contains the trailing street suffix. Example: SW."
::= { dot11APCivicLocationEntry 10 }
dot11APCivicLocationSts OBJECT-TYPE
SYNTAX OCTET STRING (SIZE(0..255))
MAX-ACCESS read-write
STATUS current
DESCRIPTION
"This is a control variable.
It is written by an external management entity or the SME.
Changes take effect as soon as practical in the implementation.
This attribute contains the street suffix. Example: Avenue, 'Platz,
Street'."
::= { dot11APCivicLocationEntry 11 }
dot11APCivicLocationHno OBJECT-TYPE
SYNTAX OCTET STRING (SIZE(0..255))
MAX-ACCESS read-write
STATUS current
DESCRIPTION
"This is a control variable.
It is written by an external management entity or the SME.
Changes take effect as soon as practical in the implementation.
This attribute contains the numeric part only of the
House number. Example: 123."
::= { dot11APCivicLocationEntry 12 }
dot11APCivicLocationHns OBJECT-TYPE
SYNTAX OCTET STRING (SIZE(0..255))
MAX-ACCESS read-write
STATUS current
DESCRIPTION
"This is a control variable.
It is written by an external management entity or the SME.
Changes take effect as soon as practical in the implementation.
This attribute contains the house number suffix. Example: A, 1/2"
::= { dot11APCivicLocationEntry 13 }
dot11APCivicLocationLmk OBJECT-TYPE
SYNTAX OCTET STRING (SIZE(0..255))
MAX-ACCESS read-write
STATUS current
DESCRIPTION
"This is a control variable.
It is written by an external management entity or the SME.
Changes take effect as soon as practical in the implementation.
This attribute contains the landmark or vanity address. Example: Low
Library."
::= { dot11APCivicLocationEntry 14 }
dot11APCivicLocationLoc OBJECT-TYPE
SYNTAX OCTET STRING (SIZE(0..255))
MAX-ACCESS read-write
STATUS current
DESCRIPTION
"This is a control variable.
It is written by an external management entity or the SME.
Changes take effect as soon as practical in the implementation.
This attribute contains additional location information. Example: Room
543."
::= { dot11APCivicLocationEntry 15 }
dot11APCivicLocationNam OBJECT-TYPE
SYNTAX OCTET STRING (SIZE(0..255))
MAX-ACCESS read-write
STATUS current
DESCRIPTION
"This is a control variable.
It is written by an external management entity or the SME.
Changes take effect as soon as practical in the implementation.
This attribute contains the name (residence, business, or office occupant.
Example: Joe.s Barbershop."
::= { dot11APCivicLocationEntry 16 }
dot11APCivicLocationPc OBJECT-TYPE
SYNTAX OCTET STRING (SIZE(0..255))
MAX-ACCESS read-write
STATUS current
DESCRIPTION
"This is a control variable.
It is written by an external management entity or the SME.
Changes take effect as soon as practical in the implementation.
This attribute contains the postal code. Example: 10027-0401."
::= { dot11APCivicLocationEntry 17 }
dot11APCivicLocationBld OBJECT-TYPE
SYNTAX OCTET STRING (SIZE(0..255))
MAX-ACCESS read-write
STATUS current
DESCRIPTION
"This is a control variable.
It is written by an external management entity or the SME.
Changes take effect as soon as practical in the implementation.
This attribute contains the building (structure). Example: Hope Theater."
::= { dot11APCivicLocationEntry 18 }
dot11APCivicLocationUnit OBJECT-TYPE
SYNTAX OCTET STRING (SIZE(0..255))
MAX-ACCESS read-write
STATUS current
DESCRIPTION
"This is a control variable.
It is written by an external management entity or the SME.
Changes take effect as soon as practical in the implementation.
This attribute contains the unit (apartment, suite). Example: 12a."
::= { dot11APCivicLocationEntry 19 }
dot11APCivicLocationFlr OBJECT-TYPE
SYNTAX OCTET STRING (SIZE(0..255))
MAX-ACCESS read-write
STATUS current
DESCRIPTION
"This is a control variable.
It is written by an external management entity or the SME.
Changes take effect as soon as practical in the implementation.
This attribute contains the floor number. Example: 5."
::= { dot11APCivicLocationEntry 20 }
dot11APCivicLocationRoom OBJECT-TYPE
SYNTAX OCTET STRING (SIZE(0..255))
MAX-ACCESS read-write
STATUS current
DESCRIPTION
"This is a control variable.
It is written by an external management entity or the SME.
Changes take effect as soon as practical in the implementation.
This attribute contains the room. Example: 450F."
::= { dot11APCivicLocationEntry 21 }
dot11APCivicLocationPlc OBJECT-TYPE
SYNTAX OCTET STRING (SIZE(0..255))
MAX-ACCESS read-write
STATUS current
DESCRIPTION
"This is a control variable.
It is written by an external management entity or the SME.
Changes take effect as soon as practical in the implementation.
This attribute contains the place type. Example: office."
::= { dot11APCivicLocationEntry 22 }
dot11APCivicLocationPcn OBJECT-TYPE
SYNTAX OCTET STRING (SIZE(0..255))
MAX-ACCESS read-write
STATUS current
DESCRIPTION
"This is a control variable.
It is written by an external management entity or the SME.
Changes take effect as soon as practical in the implementation.
This attribute contains the postal community name. Example: Leonia."
::= { dot11APCivicLocationEntry 23 }
dot11APCivicLocationPobox OBJECT-TYPE
SYNTAX OCTET STRING (SIZE(0..255))
MAX-ACCESS read-write
STATUS current
DESCRIPTION
"This is a control variable.
It is written by an external management entity or the SME.
Changes take effect as soon as practical in the implementation.
This attribute contains the post office box (P.O. Box). Example: U40."
::= { dot11APCivicLocationEntry 24 }
dot11APCivicLocationAddcode OBJECT-TYPE
SYNTAX OCTET STRING (SIZE(0..255))
MAX-ACCESS read-write
STATUS current
DESCRIPTION
"This is a control variable.
It is written by an external management entity or the SME.
Changes take effect as soon as practical in the implementation.
This attribute contains the additional code. Example: 13203000003."
::= { dot11APCivicLocationEntry 25 }
dot11APCivicLocationSeat OBJECT-TYPE
SYNTAX OCTET STRING (SIZE(0..255))
MAX-ACCESS read-write
STATUS current
DESCRIPTION
"This is a control variable.
It is written by an external management entity or the SME.
Changes take effect as soon as practical in the implementation.
This attribute contains the seat (desk, cubicle, workstation). Example: WS
181."
::= { dot11APCivicLocationEntry 26 }
dot11APCivicLocationRd OBJECT-TYPE
SYNTAX OCTET STRING (SIZE(0..255))
MAX-ACCESS read-write
STATUS current
DESCRIPTION
"This is a control variable.
It is written by an external management entity or the SME.
Changes take effect as soon as practical in the implementation.
This attribute contains the primary road or street. Example: Broadway."
::= { dot11APCivicLocationEntry 27 }
dot11APCivicLocationRdsec OBJECT-TYPE
SYNTAX OCTET STRING (SIZE(0..255))
MAX-ACCESS read-write
STATUS current
DESCRIPTION
"This is a control variable.
It is written by an external management entity or the SME.
Changes take effect as soon as practical in the implementation.
This attribute contains the road section. Example: 14.In some countries a
thoroughfare can be broken up into sections, and it is not uncommon for
street numbers to be repeated between sections. A road section identifier
is required to ensure that an address is unique. For example, West Alice
Parade has 5 sections, each numbered from 1; unless the section is specified
7 West Alice Parade could exist in 5 different places."
::= { dot11APCivicLocationEntry 28 }
dot11APCivicLocationRdbr OBJECT-TYPE
SYNTAX OCTET STRING (SIZE(0..255))
MAX-ACCESS read-write
STATUS current
DESCRIPTION
"This is a control variable.
It is written by an external management entity or the SME.
Changes take effect as soon as practical in the implementation.
This attribute contains the road branch. Example: 'Lane 7'. Minor streets
can share the same name, so that they can only Be distinguished by the
major thoroughfare with which they intersect. For example, both West Alice
Parade, Section 3 and Bob Street could both be interested by a Carol Lane.
This element is used to specify a road branch where the name of the branch
does not uniquely identify the road. Road branches MAY also be used where
a major thoroughfare is split into sections."
::= { dot11APCivicLocationEntry 29 }
dot11APCivicLocationRdsubbr OBJECT-TYPE
SYNTAX OCTET STRING (SIZE(0..255))
MAX-ACCESS read-write
STATUS current
DESCRIPTION
"This is a control variable.
It is written by an external management entity or the SME.
Changes take effect as soon as practical in the implementation.
This attribute contains the road sub-branch. Example: Alley 8."
::= { dot11APCivicLocationEntry 30 }
dot11APCivicLocationPrm OBJECT-TYPE
SYNTAX OCTET STRING (SIZE(0..255))
MAX-ACCESS read-write
STATUS current
DESCRIPTION
"This is a control variable.
It is written by an external management entity or the SME.
Changes take effect as soon as practical in the implementation.
This attribute contains the road premodifier. Example: Old."
::= { dot11APCivicLocationEntry 31 }
dot11APCivicLocationPom OBJECT-TYPE
SYNTAX OCTET STRING (SIZE(0..255))
MAX-ACCESS read-write
STATUS current
DESCRIPTION
"This is a control variable.
It is written by an external management entity or the SME.
Changes take effect as soon as practical in the implementation.
This attribute contains the road post-modifier. Example: Extended."
::= { dot11APCivicLocationEntry 32 }
-- **********************************************************************
-- * End of dot11APCivicLocation TABLE
-- **********************************************************************
-- **********************************************************************
-- * dot11RoamingConsortium TABLE
-- **********************************************************************
dot11RoamingConsortiumTable OBJECT-TYPE
SYNTAX SEQUENCE OF Dot11RoamingConsortiumEntry
MAX-ACCESS not-accessible
STATUS current
DESCRIPTION
"This is a Table of OIs which are to be transmitted in an ANQP Roaming
Consortium ANQP-element. Each table entry corresponds to a roaming consortium
or single SSP. The first 3 entries in this table are transmitted in
Beacon and Probe Response frames."
::= { dot11imt 5 }
dot11RoamingConsortiumEntry OBJECT-TYPE
SYNTAX Dot11RoamingConsortiumEntry
MAX-ACCESS not-accessible
STATUS current
DESCRIPTION
"Each OI identifies a roaming consortium (group of SSPs with inter-SSP
roaming agreement) or a single SSP. A non-AP STA in possession of security
credentials for the SSPN(s) identified by the OI, should be able to successfully
authenticate to this AP."
INDEX { dot11RoamingConsortiumOI }
::= { dot11RoamingConsortiumTable 1 }
Dot11RoamingConsortiumEntry ::=
SEQUENCE {
dot11RoamingConsortiumOI OCTET STRING,
dot11RoamingConsortiumRowStatus RowStatus
}
dot11RoamingConsortiumOI OBJECT-TYPE
SYNTAX OCTET STRING (SIZE(16))
MAX-ACCESS not-accessible
STATUS current
DESCRIPTION
"This is a control variable.
It is written by an external management entity or the SME.
Changes take effect as soon as practical in the implementation.
This attribute contains the IEEE defined OI as defined in 8.4.1.31."
::= { dot11RoamingConsortiumEntry 1 }
dot11RoamingConsortiumRowStatus OBJECT-TYPE
SYNTAX RowStatus
MAX-ACCESS read-create
STATUS current
DESCRIPTION
"This object represents the status column for a conceptual row in this
table."
::= { dot11RoamingConsortiumEntry 2 }
-- **********************************************************************
-- * End of dot11RoamingConsortium TABLE
-- **********************************************************************
-- **********************************************************************
-- * dot11DomainName TABLE
-- **********************************************************************
dot11DomainNameTable OBJECT-TYPE
SYNTAX SEQUENCE OF Dot11DomainNameEntry
MAX-ACCESS not-accessible
STATUS current
DESCRIPTION
"This is a table of Domain Names which form the Domain Name list in Access
Network Query Protocol. The Domain Name list may be transmitted to a non-
AP STA in a GAS Response. Each table entry corresponds to a single Domain
Name."
::= { dot11imt 6 }
dot11DomainNameEntry OBJECT-TYPE
SYNTAX Dot11DomainNameEntry
MAX-ACCESS not-accessible
STATUS current
DESCRIPTION
"This is a control variable.
It is written by an external management entity or the SME.
Changes take effect as soon as practical in the implementation.
Each Domain Name identifies a domain names of the entity operating the
IEEE 802.11 access network."
INDEX { dot11DomainNameOui }
::= { dot11DomainNameTable 1 }
Dot11DomainNameEntry ::=
SEQUENCE {
dot11DomainName OCTET STRING,
dot11DomainNameRowStatus RowStatus,
dot11DomainNameOui OCTET STRING
}
dot11DomainName OBJECT-TYPE
SYNTAX OCTET STRING (SIZE(255))
MAX-ACCESS read-write
STATUS current
DESCRIPTION
"This is a control variable.
It is written by an external management entity or the SME.
Changes take effect as soon as practical in the implementation.
This attribute contains a Domain Name of up to 255 octets formatted in
accordance with the 'Preferred Name Syntax' as defined in IETF RFC 1035."
::= { dot11DomainNameEntry 1 }
dot11DomainNameRowStatus OBJECT-TYPE
SYNTAX RowStatus
MAX-ACCESS read-create
STATUS current
DESCRIPTION
"This object represents the status column for a conceptual row in this
table."
::= { dot11DomainNameEntry 2 }
dot11DomainNameOui OBJECT-TYPE
SYNTAX OCTET STRING (SIZE(3..5))
MAX-ACCESS not-accessible
STATUS current
DESCRIPTION
"This object represents an organizationally unique identifier, used as an
index into the Domain Name table."
::= { dot11DomainNameEntry 3 }
-- **********************************************************************
-- * End of dot11NameTable TABLE
-- **********************************************************************
-- **********************************************************************
-- * dot11GASAdvertisement TABLE
-- **********************************************************************
dot11GASAdvertisementTable OBJECT-TYPE
SYNTAX SEQUENCE OF Dot11GASAdvertisementEntry
MAX-ACCESS not-accessible
STATUS current
DESCRIPTION
"This object is a table of GAS counters that allows for multiple instantiations
of those counters on an STA."
::= { dot11imt 7 }
dot11GASAdvertisementEntry OBJECT-TYPE
SYNTAX Dot11GASAdvertisementEntry
MAX-ACCESS not-accessible
STATUS current
DESCRIPTION
"This object provides the attributes identifying a GAS counter within an
STA."
INDEX { dot11GASAdvertisementId }
::= { dot11GASAdvertisementTable 1 }
Dot11GASAdvertisementEntry ::=
SEQUENCE{
dot11GASAdvertisementId Unsigned32,
dot11GASPauseForServerResponse TruthValue,
dot11GASResponseTimeout Unsigned32,
dot11GASComebackDelay Unsigned32,
dot11GASResponseBufferingTime Unsigned32,
dot11GASQueryResponseLengthLimit Unsigned32,
dot11GASQueries Counter32,
dot11GASQueryRate Gauge32,
dot11GASResponses Counter32,
dot11GASResponseRate Gauge32,
dot11GASTransmittedFragmentCount Counter32,
dot11GASReceivedFragmentCount Counter32,
dot11GASNoRequestOutstanding Counter32,
dot11GASResponsesDiscarded Counter32,
dot11GASFailedResponses Counter32
}
dot11GASAdvertisementId OBJECT-TYPE
SYNTAX Unsigned32 (0..255)
MAX-ACCESS not-accessible
STATUS current
DESCRIPTION
"This is a control variable.
It is written by an external management entity or the SME.
Changes take effect as soon as practical in the implementation.
The 1 octet identification number for the GAS Advertisement Protocol, as
defined in Table 8-175, for which statistics are stored the logical row of
the GASAdvertisement table."
::= { dot11GASAdvertisementEntry 1 }
dot11GASPauseForServerResponse OBJECT-TYPE
SYNTAX TruthValue
MAX-ACCESS read-write
STATUS current
DESCRIPTION
"This is a control variable.
It is written by an external management entity or the SME.
Changes take effect as soon as practical in the implementation.
This attribute is only used by the responding STA in a GAS exchange. When
true, it indicates that the responding STA will not transmit a GAS Initial
Response frame until it receives the query response from the Advertisement
Server or a timeout occurs. When false, the STA will not wait for a
response from the Advertisement Server before transmiting the GAS Initial
Response frame. The setting of this MIB object is outside the scope of
this standard."
::= { dot11GASAdvertisementEntry 2 }
dot11GASResponseTimeout OBJECT-TYPE
SYNTAX Unsigned32 (1000..65535)
MAX-ACCESS read-write
STATUS current
DESCRIPTION
"This is a control variable.
It is written by an external management entity or the SME.
Changes take effect as soon as practical in the implementation.
This parameter shall indicate the GAS response timeout value in TUs."
DEFVAL {5000}
::= { dot11GASAdvertisementEntry 3 }
dot11GASComebackDelay OBJECT-TYPE
SYNTAX Unsigned32 (0..65535)
MAX-ACCESS read-write
STATUS current
DESCRIPTION
"This is a control variable.
It is written by an external management entity or the SME.
Changes take effect as soon as practical in the implementation.
This object identifies the GAS Comeback Delay (in TUs) to be used for this
Advertisement Protocol"
DEFVAL {1000}
::= { dot11GASAdvertisementEntry 4 }
dot11GASResponseBufferingTime OBJECT-TYPE
SYNTAX Unsigned32 (0..65535)
MAX-ACCESS read-write
STATUS current
DESCRIPTION
"This is a control variable.
It is written by an external management entity or the SME.
Changes take effect as soon as practical in the implementation.
This object defines the time duration after the expiry of the GAS Comeback
Delay that an STA will buffer a Query Response. The units of this MIB
object are TUs. Upon expiry of this time, the STA may discard the Query
Response."
DEFVAL {1000}
::= { dot11GASAdvertisementEntry 5 }
dot11GASQueryResponseLengthLimit OBJECT-TYPE
SYNTAX Unsigned32 (1..127)
MAX-ACCESS read-write
STATUS current
DESCRIPTION
"This is a control variable.
It is written by an external management entity or the SME.
Changes take effect as soon as practical in the implementation.
This object indicates the maximum number of octets an AP will transmit in
one or more Query Response fields contained within GAS Comeback Response
frame(s). A value of 127 means the maximum limit enforced is contained by
the maximum allowable number of fragments in the GAS Query Fragment
Response ID"
::= { dot11GASAdvertisementEntry 6 }
dot11GASQueries OBJECT-TYPE
SYNTAX Counter32
MAX-ACCESS read-only
STATUS current
DESCRIPTION
"This is a status variable.
It is written by the SME after transmission of a MLME-GAS.request or
receipt of an MLME-GAS.indication primitive.
The number of GAS queries sent or received for the protocol identified by
dot11GASAdvertisementId."
::= { dot11GASAdvertisementEntry 7 }
dot11GASQueryRate OBJECT-TYPE
SYNTAX Gauge32
MAX-ACCESS read-only
STATUS current
DESCRIPTION
"This is a status variable.
It is updated by the SME after receipt of an MLME-GAS.indication primitive.
The number of GAS queries per minute received for the protocol identified
by dot11GASAdvertisementId, averaged over the previous ten minutes."
::= { dot11GASAdvertisementEntry 8 }
dot11GASResponses OBJECT-TYPE
SYNTAX Counter32
MAX-ACCESS read-only
STATUS current
DESCRIPTION
"This is a status variable.
It is written by the SME after transmission of a MLME-GAS.response or
receipt of an MLME-GAS.confirm primitive.
The number of GAS responses sent or received for the protocol identified
by dot11GASAdvertisementId."
::= { dot11GASAdvertisementEntry 9 }
dot11GASResponseRate OBJECT-TYPE
SYNTAX Gauge32
MAX-ACCESS read-only
STATUS current
DESCRIPTION
"This is a status variable.
It is updated by the SME after transmission of an MLME-GAS.response primitive.
The number of responses to GAS queries per minute transmitted by an AP for
the protocol identified by dot11GASAdvertisementId, averaged over the previous
ten minutes. This MIB variable is not used in non-AP STAs."
::= { dot11GASAdvertisementEntry 10 }
dot11GASTransmittedFragmentCount OBJECT-TYPE
SYNTAX Counter32
MAX-ACCESS read-only
STATUS current
DESCRIPTION
"This is a status variable.
It is updated by the SME after transmission of an MLME-GAS.response primitive.
This counter shall be incremented for an acknowledged GAS MMPDU for the
protocol identified by dot11GASAdvertisementId."
::= { dot11GASAdvertisementEntry 11 }
dot11GASReceivedFragmentCount OBJECT-TYPE
SYNTAX Counter32
MAX-ACCESS read-only
STATUS current
DESCRIPTION
"This is a status variable.
It is updated by the MAC after transmission of an MLME-GAS.confirm primitive.
This counter shall be incremented for each successfully received MMPDU of
type Data"
::= { dot11GASAdvertisementEntry 12 }
dot11GASNoRequestOutstanding OBJECT-TYPE
SYNTAX Counter32
MAX-ACCESS read-only
STATUS current
DESCRIPTION
"This is a status variable.
It is updated by the SME after transmission of an MLME-GAS.response primitive.
This counter shall be incremented each time a STA returns a status code of
no request outstanding in a GAS Initial Response or GAS Comeback Response
frame for the protocol identified by dot11GASAdvertisementId."
::= { dot11GASAdvertisementEntry 13 }
dot11GASResponsesDiscarded OBJECT-TYPE
SYNTAX Counter32
MAX-ACCESS read-only
STATUS current
DESCRIPTION
"This is a status variable.
It is updated by the SME after transmission of an MLME-GAS.response primitive.
This counter shall be incremented each a STA discards a GAS response due
to the expiry of the dot11GASResponseBufferingTime timer for the protocol
identified by dot11GASAdvertisementId."
::= { dot11GASAdvertisementEntry 14 }
dot11GASFailedResponses OBJECT-TYPE
SYNTAX Counter32
MAX-ACCESS read-only
STATUS current
DESCRIPTION
"This is a status variable.
It is updated by the SME after transmission of an MLME-GAS.response primitive.
This counter shall be incremented each time a STA commences transmitting a
GAS response but fails to successfully complete the transmission of all
GAS fragments in that response due to the expiry of the
dot11GASResponseTimeout timer for the protocol identified by
dot11GASAdvertisementId."
::= { dot11GASAdvertisementEntry 15 }
-- **********************************************************************
-- * End of dot11GASAdvertisement TABLE
-- **********************************************************************
-- **********************************************************************
-- * MAC State Generic Convergence
-- **********************************************************************
-- MAC State Generic Convergence Function attributes
-- DEFINED AS "The MAC state generic convergence function object
-- class provides the necessary support for support of event-driven
-- triggers to higher layer protocols and the capabilities to
-- support those triggers."
dot11MSGCF OBJECT IDENTIFIER ::= { ieee802dot11 7}
-- MAC State GROUPS
-- dot11MACStateConfigTable ::= { dot11MSGCF 1 }
-- dot11MACStateParameterTable ::= { dot11MSGCF 2 }
-- dot11MACStateESSLinkTable ::= { dot11MSGCF 3 }
-- *********************************************************************
-- * dot11ESSLinkIdentifier type definition
-- *********************************************************************
--Dot11ESSLinkIdentifier ::= OCTET STRING (SIZE(0..38))
Dot11ESSLinkIdentifier ::= TEXTUAL-CONVENTION
    DISPLAY-HINT "d"
    STATUS      current
    DESCRIPTION ""
    SYNTAX OCTET STRING (SIZE(0..38))
-- This object type holds the identifier for an 802.11
-- network. It is composed of the SSID string concatenated
-- with the HESSID, if present.
-- *********************************************************************
-- * dot11MACStateConfig TABLE
-- *********************************************************************
dot11MACStateConfigTable OBJECT-TYPE
SYNTAX SEQUENCE OF Dot11MACStateConfigEntry
MAX-ACCESS not-accessible
STATUS current
DESCRIPTION
"This table holds configuration parameters for the 802.11 MAC
State Convergence Function."
::= { dot11MSGCF 1 }
dot11MACStateConfigEntry OBJECT-TYPE
SYNTAX Dot11MACStateConfigEntry
MAX-ACCESS not-accessible
STATUS current
DESCRIPTION
"Each entry represents a conceptual row in the dot11MACStateConfigTable
and provides information about network configuration parameters used in
the MAC State Generic Convergence Function."
INDEX { dot11MSCEESSLinkIdentifier, dot11MSCENonAPStationMacAddress }
::= { dot11MACStateConfigTable 1 }
Dot11MACStateConfigEntry ::=
SEQUENCE {
dot11ESSDisconnectFilterInterval Unsigned32,
dot11ESSLinkDetectionHoldInterval Unsigned32,
dot11MSCEESSLinkIdentifier Dot11ESSLinkIdentifier,
dot11MSCENonAPStationMacAddress MacAddress
}
dot11ESSDisconnectFilterInterval OBJECT-TYPE
SYNTAX Unsigned32
MAX-ACCESS read-write
STATUS current
DESCRIPTION
"This is a control variable.
It is written by an external management entity or the SME.
Changes take effect as soon as practical in the implementation.
This attribute is set to the number of time units (TUs) that will elapse
after an MLME-DISASSOCIATE.confirm or MLME-DEAUTHENTICATE.confirm primitive
without a subsequent association before the link is declared down.
This interval is intended to allow a non-AP STA time to transition to
another AP within the same ESS before declaring that the link to the ESS
is lost."
::= { dot11MACStateConfigEntry 1 }
dot11ESSLinkDetectionHoldInterval OBJECT-TYPE
SYNTAX Unsigned32
MAX-ACCESS read-write
STATUS current
DESCRIPTION
"This is a control variable.
It is written by an external management entity or the SME.
Changes take effect as soon as practical in the implementation.
This attribute is set to the number of time units (TUs) that an ESS is
held in the dot11MACStateESSLink table after its last observation before
purging the entry from the table."
::= { dot11MACStateConfigEntry 2 }
dot11MSCEESSLinkIdentifier OBJECT-TYPE
SYNTAX Dot11ESSLinkIdentifier
MAX-ACCESS not-accessible
STATUS current
DESCRIPTION
"This is an auxiliary variable used to identify instances of the columnar
objects in the dot11MACStateConfigTable table."
::= { dot11MACStateConfigEntry 3 }
dot11MSCENonAPStationMacAddress OBJECT-TYPE
SYNTAX MacAddress
MAX-ACCESS not-accessible
STATUS current
DESCRIPTION
"This is an auxiliary variable used to identify instances of the columnar
objects in the dot11MACStateConfigTable table."
::= { dot11MACStateConfigEntry 4 }
-- *********************************************************************
-- * End of dot11MACStateConfig TABLE
-- *********************************************************************
-- *********************************************************************
-- * dot11MACStateParameter TABLE
-- *********************************************************************
dot11MACStateParameterTable OBJECT-TYPE
SYNTAX SEQUENCE OF Dot11MACStateParameterEntry
MAX-ACCESS not-accessible
STATUS current
DESCRIPTION
"This table holds the current parameters used for each 802.11 network for
802.11 MAC convergence functions."
::= { dot11MSGCF 2 }
dot11MACStateParameterEntry OBJECT-TYPE
SYNTAX Dot11MACStateParameterEntry
MAX-ACCESS not-accessible
STATUS current
DESCRIPTION
"Each entry represents a conceptual row in the dot11MACStateParameterTable
and provides information about link configuration parameters used in the
MAC State Generic Convergence Function."
INDEX { dot11MSPEESSLinkIdentifier, dot11MSPENonAPStationMacAddress }
::= { dot11MACStateParameterTable 1 }
Dot11MACStateParameterEntry ::=
SEQUENCE {
dot11ESSLinkDownTimeInterval Unsigned32,
dot11ESSLinkRssiDataThreshold Unsigned32,
dot11ESSLinkRssiBeaconThreshold Unsigned32,
dot11ESSLinkDataSnrThreshold Unsigned32,
dot11ESSLinkBeaconSnrThreshold Unsigned32,
dot11ESSLinkBeaconFrameErrorRateThresholdInteger Unsigned32,
dot11ESSLinkBeaconFrameErrorRateThresholdFraction Unsigned32,
dot11ESSLinkBeaconFrameErrorRateThresholdExponent Unsigned32,
dot11ESSLinkFrameErrorRateThresholdInteger Unsigned32,
dot11ESSLinkFrameErrorRateThresholdFraction Unsigned32,
dot11ESSLinkFrameErrorRateThresholdExponent Unsigned32,
dot11PeakOperationalRate Unsigned32,
dot11MinimumOperationalRate Unsigned32,
dot11ESSLinkDataThroughputInteger Unsigned32,
dot11ESSLinkDataThroughputFraction Unsigned32,
dot11ESSLinkDataThroughputExponent Unsigned32,
dot11MSPEESSLinkIdentifier Dot11ESSLinkIdentifier,
dot11MSPENonAPStationMacAddress MacAddress
}
dot11ESSLinkDownTimeInterval OBJECT-TYPE
SYNTAX Unsigned32
MAX-ACCESS read-write
STATUS current
DESCRIPTION
"This is a control variable.
It is written by an external management entity or the SME.
Changes take effect as soon as practical in the implementation.
This attribute defines the desired time interval that the MAC State
Generic convergence function will attempt to predict the failure of an
802.11 network in time units (TUs). The convergence function should issue
predicted network failure events at least this time interval before the
network failure is detected."
::= { dot11MACStateParameterEntry 2 }
dot11ESSLinkRssiDataThreshold OBJECT-TYPE
SYNTAX Unsigned32
MAX-ACCESS read-write
STATUS current
DESCRIPTION
"This is a control variable.
It is written by an external management entity or the SME.
Changes take effect as soon as practical in the implementation.
This attribute defines the threshold value for RSSI on Data frames. When
the RSSI drops below this threshold, a report is issued."
::= { dot11MACStateParameterEntry 3 }
dot11ESSLinkRssiBeaconThreshold OBJECT-TYPE
SYNTAX Unsigned32
MAX-ACCESS read-write
STATUS current
DESCRIPTION
"This is a control variable.
It is written by an external management entity or the SME.
Changes take effect as soon as practical in the implementation.
This attribute defines the threshold value for RSSI on Beacon frames. When
the RSSI drops below this threshold, a report is issued."
::= { dot11MACStateParameterEntry 4 }
dot11ESSLinkBeaconSnrThreshold OBJECT-TYPE
SYNTAX Unsigned32
MAX-ACCESS read-write
STATUS current
DESCRIPTION
"This is a control variable.
It is written by an external management entity or the SME.
Changes take effect as soon as practical in the implementation.
This attribute defines the threshold value for SNR on received Beacon
frames. When the SNR drops below this threshold, a report is issued"
::= { dot11MACStateParameterEntry 5 }
dot11ESSLinkDataSnrThreshold OBJECT-TYPE
SYNTAX Unsigned32
MAX-ACCESS read-write
STATUS current
DESCRIPTION
"This is a control variable.
It is written by an external management entity or the SME.
Changes take effect as soon as practical in the implementation.
This attribute defines the threshold value for SNR on received Data
frames. When the SNR drops below this threshold, a report is issued."
::= { dot11MACStateParameterEntry 6 }
dot11ESSLinkBeaconFrameErrorRateThresholdInteger OBJECT-TYPE
SYNTAX Unsigned32
MAX-ACCESS read-write
STATUS current
DESCRIPTION
"This is a control variable.
It is written by an external management entity or the SME.
Changes take effect as soon as practical in the implementation.
The Beacon frame error rate is stored in scientific notation as a significant
and exponent. This attribute contains the integer value of the significand."
::= { dot11MACStateParameterEntry 7 }
dot11ESSLinkBeaconFrameErrorRateThresholdFraction OBJECT-TYPE
SYNTAX Unsigned32
MAX-ACCESS read-write
STATUS current
DESCRIPTION
"This is a control variable.
It is written by an external management entity or the SME.
Changes take effect as soon as practical in the implementation.
The Beacon frame error rate is stored in scientific notation as a significant
and exponent. This attribute contains the fractional value of the
significand."
::= { dot11MACStateParameterEntry 8 }
dot11ESSLinkBeaconFrameErrorRateThresholdExponent OBJECT-TYPE
SYNTAX Unsigned32
MAX-ACCESS read-write
STATUS current
DESCRIPTION
"This is a control variable.
It is written by an external management entity or the SME.
Changes take effect as soon as practical in the implementation.
The Beacon frame error rate is stored in scientific notation as a significant
and exponent. This attribute contains the integer value of the exponent."
::= { dot11MACStateParameterEntry 9 }
dot11ESSLinkFrameErrorRateThresholdInteger OBJECT-TYPE
SYNTAX Unsigned32
MAX-ACCESS read-write
STATUS current
DESCRIPTION
"This is a control variable.
It is written by an external management entity or the SME.
Changes take effect as soon as practical in the implementation.
The frame error rate of the network is stored in scientific notation as a
significant and exponent. This attribute contains the integer value of the
significand."
::= { dot11MACStateParameterEntry 10 }
dot11ESSLinkFrameErrorRateThresholdFraction OBJECT-TYPE
SYNTAX Unsigned32
MAX-ACCESS read-write
STATUS current
DESCRIPTION
"This is a control variable.
It is written by an external management entity or the SME.
Changes take effect as soon as practical in the implementation.
The frame error rate of the network is stored in scientific notation as a
significant and exponent. This attribute contains the fractional value of
the significand."
::= { dot11MACStateParameterEntry 11 }
dot11ESSLinkFrameErrorRateThresholdExponent OBJECT-TYPE
SYNTAX Unsigned32
MAX-ACCESS read-write
STATUS current
DESCRIPTION
"This is a control variable.
It is written by an external management entity or the SME.
Changes take effect as soon as practical in the implementation.
The frame error rate of the network is stored in scientific notation as a
significant and exponent. This attribute contains the integer value of the
exponent."
::= { dot11MACStateParameterEntry 12 }
dot11PeakOperationalRate OBJECT-TYPE
SYNTAX Unsigned32
MAX-ACCESS read-write
STATUS current
DESCRIPTION
"This is a control variable.
It is written by an external management entity or the SME.
Changes take effect as soon as practical in the implementation.
The highest operational rate used for transmission of data frames, encoded
as defined in 8.4.2.3."
::= { dot11MACStateParameterEntry 13 }
dot11MinimumOperationalRate OBJECT-TYPE
SYNTAX Unsigned32
MAX-ACCESS read-write
STATUS current
DESCRIPTION
"This is a control variable.
It is written by an external management entity or the SME.
Changes take effect as soon as practical in the implementation.
The lowest operational rate used for transmission of data frames, encoded
as defined in 8.4.2.3."
::= { dot11MACStateParameterEntry 14 }
dot11ESSLinkDataThroughputInteger OBJECT-TYPE
SYNTAX Unsigned32
MAX-ACCESS read-write
STATUS current
DESCRIPTION
"This is a control variable.
It is written by an external management entity or the SME.
Changes take effect as soon as practical in the implementation.
The data throughput rate is of the network is stored in scientific notation
as a significant and exponent. This attribute contains the integer
value of the significand."
::= { dot11MACStateParameterEntry 15 }
dot11ESSLinkDataThroughputFraction OBJECT-TYPE
SYNTAX Unsigned32
MAX-ACCESS read-write
STATUS current
DESCRIPTION
"This is a control variable.
It is written by an external management entity or the SME.
Changes take effect as soon as practical in the implementation.
The data throughput rate is of the network is stored in scientific notation
as a significant and exponent. This attribute contains the fractional
value of the significand."
::= { dot11MACStateParameterEntry 16 }
dot11ESSLinkDataThroughputExponent OBJECT-TYPE
SYNTAX Unsigned32
MAX-ACCESS read-write
STATUS current
DESCRIPTION
"This is a control variable.
It is written by an external management entity or the SME.
Changes take effect as soon as practical in the implementation.
The data throughput rate is of the network is stored in scientific notation
as a significant and exponent. This attribute contains the integer
value of the exponent."
::= { dot11MACStateParameterEntry 17 }
dot11MSPEESSLinkIdentifier OBJECT-TYPE
SYNTAX Dot11ESSLinkIdentifier
MAX-ACCESS not-accessible
STATUS current
DESCRIPTION
"This is an auxiliary variable used to identify instances of the columnar
objects in the dot11MACStateParameterTable table."
::= { dot11MACStateParameterEntry 18 }
dot11MSPENonAPStationMacAddress OBJECT-TYPE
SYNTAX MacAddress
MAX-ACCESS not-accessible
STATUS current
DESCRIPTION
"This is an auxiliary variable used to identify instances of the columnar
objects in the dot11MACStateParameterTable table."
::= { dot11MACStateParameterEntry 19 }
-- *********************************************************************
-- * End of dot11MACStateParameter TABLE
-- *********************************************************************
-- *********************************************************************
-- * dot11MACStateESSLink TABLE
-- *********************************************************************
dot11MACStateESSLinkDetectedTable OBJECT-TYPE
SYNTAX SEQUENCE OF Dot11MACStateESSLinkDetectedEntry
MAX-ACCESS not-accessible
STATUS current
DESCRIPTION
"This table holds the detected 802.11 network list used for MAC convergence
functions."
::= { dot11MSGCF 3 }
dot11MACStateESSLinkDetectedEntry OBJECT-TYPE
SYNTAX Dot11MACStateESSLinkDetectedEntry
MAX-ACCESS not-accessible
STATUS current
DESCRIPTION
"Each entry represents a conceptual row in the dot11MACStateESSLinkTable
and provides information about available networks for use in the MAC State
Generic Convergence Function."
INDEX { dot11MSELDEESSLinkIdentifier, dot11MSELDENonAPStationMacAddress }
::= { dot11MACStateESSLinkDetectedTable 1 }
Dot11MACStateESSLinkDetectedEntry ::=
SEQUENCE {
dot11ESSLinkDetectedIndex Unsigned32,
dot11ESSLinkDetectedNetworkId OCTET STRING,
dot11ESSLinkDetectedNetworkDetectTime Unsigned32,
dot11ESSLinkDetectedNetworkModifiedTime Unsigned32,
dot11ESSLinkDetectedNetworkMIHCapabilities BITS,
dot11MSELDEESSLinkIdentifier Dot11ESSLinkIdentifier,
dot11MSELDENonAPStationMacAddress MacAddress
}
dot11ESSLinkDetectedIndex OBJECT-TYPE
SYNTAX Unsigned32
MAX-ACCESS not-accessible
STATUS current
DESCRIPTION
"Index for ESSLinkDetected elements in dot11ESSLinkDetectedTable, greater
than 0."
::= { dot11MACStateESSLinkDetectedEntry 1 }
dot11ESSLinkDetectedNetworkId OBJECT-TYPE
SYNTAX OCTET STRING
MAX-ACCESS read-only
STATUS current
DESCRIPTION
"This is a status variable.
It is written by the MSGCF after reception of a MSGCF-ESS-Link-
Detected.indication primitive.
The string used to identify the network represented by this row in the
table. It is composed of the SSID of the network concatenated with the
HESSID, if present."
::= { dot11MACStateESSLinkDetectedEntry 2 }
dot11ESSLinkDetectedNetworkDetectTime OBJECT-TYPE
SYNTAX Unsigned32
MAX-ACCESS read-only
STATUS current
DESCRIPTION
"This is a status variable.
It is written by the MSGCF after reception of a MSGCF-ESS-Link-
Detected.indication primitive.
The STA's TSF timer when any BSSID supporting the network was first
detected."
::= { dot11MACStateESSLinkDetectedEntry 4 }
dot11ESSLinkDetectedNetworkModifiedTime OBJECT-TYPE
SYNTAX Unsigned32
MAX-ACCESS read-only
STATUS current
DESCRIPTION
"This is a status variable.
It is written by the MSGCF after reception of a MSGCF-ESS-Link-
Detected.indication primitive.
The STA's TSF timer value when changes were made to any part of this row
in the table, such as by addition of a BSSID to the BSSID list."
::= { dot11MACStateESSLinkDetectedEntry 5 }
dot11ESSLinkDetectedNetworkMIHCapabilities OBJECT-TYPE
SYNTAX BITS {
mihIsSupport(0),
mihCsEsSupport(1)
}
MAX-ACCESS read-only
STATUS current
DESCRIPTION
"This is a status variable.
It is written by the MSGCF after reception of a MSGCF-ESS-Link-
Detected.indication primitive.
The object reports whether the network supports IEEE 802.21 MIH information
services and/or IEEE 802.21 MIH command/event services. These values
are determined by examining the Interworking information in frames that
caused the network to be detected."
::= { dot11MACStateESSLinkDetectedEntry 6 }
dot11MSELDEESSLinkIdentifier OBJECT-TYPE
SYNTAX Dot11ESSLinkIdentifier
MAX-ACCESS not-accessible
STATUS current
DESCRIPTION
"This is an auxiliary variable used to identify instances of the columnar
objects in the dot11MACStateESSLinkDetectedTable table."
::= { dot11MACStateESSLinkDetectedEntry 7 }
dot11MSELDENonAPStationMacAddress OBJECT-TYPE
SYNTAX MacAddress
MAX-ACCESS not-accessible
STATUS current
DESCRIPTION
"This is an auxiliary variable used to identify instances of the columnar
objects in the dot11MACStateESSLinkDetectedTable table."
::= { dot11MACStateESSLinkDetectedEntry 8 }
-- *********************************************************************
-- * End of dot11MACStateESSLink TABLE
-- *********************************************************************
-- **********************************************************************
-- * Conformance Information
-- **********************************************************************
dot11Conformance OBJECT IDENTIFIER ::= { ieee802dot11 5 }
dot11Groups OBJECT IDENTIFIER ::= { dot11Conformance 1 }
dot11Compliances OBJECT IDENTIFIER ::= { dot11Conformance 2 }
-- **********************************************************************
-- * Groups - units of conformance
-- **********************************************************************
dot11SMTbase OBJECT-GROUP
OBJECTS {
dot11StationID,
dot11MediumOccupancyLimit,
dot11CFPollable,
dot11CFPPeriod,
dot11CFPMaxDuration,
dot11AuthenticationResponseTimeOut,
dot11PrivacyOptionImplemented,
dot11PowerManagementMode,
dot11DesiredSSID, dot11DesiredBSSType,
dot11OperationalRateSet,
dot11BeaconPeriod, dot11DTIMPeriod,
dot11AssociationResponseTimeOut }
STATUS deprecated
DESCRIPTION
"Superseded by dot11SMTbase2.
The SMT object class provides the necessary support at the STA to manage
the processes in the STA such that the STA may work cooperatively as a
part of an IEEE 802.11 network."
::= { dot11Groups 1 }
dot11SMTprivacy OBJECT-GROUP
OBJECTS {
dot11PrivacyInvoked,
dot11WEPKeyMappingLengthImplemented,
dot11ExcludeUnencrypted,
dot11WEPICVErrorCount,
dot11WEPExcludedCount,
dot11WEPDefaultKeyID,
dot11WEPDefaultKeyValue,
dot11WEPKeyMappingWEPOn,
dot11WEPKeyMappingValue,
dot11WEPKeyMappingAddress,
dot11WEPKeyMappingStatus }
STATUS current
DESCRIPTION
"The SMTPrivacy package is a set of attributes that are present if WEP is
implemented in the STA."
::= { dot11Groups 2 }
dot11MACbase OBJECT-GROUP
OBJECTS {
dot11MACAddress,
dot11Address,
dot11GroupAddressesStatus,
dot11RTSThreshold,
dot11ShortRetryLimit,
dot11LongRetryLimit,
dot11FragmentationThreshold,
dot11MaxTransmitMSDULifetime,
dot11MaxReceiveLifetime,
dot11ManufacturerID,
dot11ProductID }
STATUS deprecated
DESCRIPTION
"Superseded by dot11MACbase2.
The MAC object class provides the necessary support for the access control,
generation, and verification of frame check sequences (FCSs), and
proper delivery of valid data to upper layers."
::= { dot11Groups 3 }
dot11MACStatistics OBJECT-GROUP
OBJECTS {
dot11RetryCount,
dot11MultipleRetryCount,
dot11RTSSuccessCount,
dot11RTSFailureCount,
dot11ACKFailureCount,
dot11FrameDuplicateCount }
STATUS current
DESCRIPTION
"The MACStatistics package provides extended statistical information on
the operation of the MAC. This package is completely optional."
::= { dot11Groups 4 }
dot11ResourceTypeID OBJECT-GROUP
OBJECTS {
dot11ResourceTypeIDName,
dot11manufacturerOUI,
dot11manufacturerName,
dot11manufacturerProductName,
dot11manufacturerProductVersion }
STATUS current
DESCRIPTION
"Attributes used to identify a STA, its manufacturer, and various product
names and versions."
::= { dot11Groups 5 }
dot11SmtAuthenticationAlgorithms OBJECT-GROUP
OBJECTS {
dot11AuthenticationAlgorithm,
dot11AuthenticationAlgorithmsActivated }
STATUS current
DESCRIPTION
"Authentication Algorithm Table."
::= { dot11Groups 6 }
dot11PhyOperationComplianceGroup OBJECT-GROUP
OBJECTS { dot11PHYType, dot11CurrentRegDomain, dot11TempType }
STATUS deprecated
DESCRIPTION
"Superseded by dot11PhyOperationComplianceGroup2.
PHY layer operations attributes."
::= { dot11Groups 7 }
dot11PhyAntennaComplianceGroup OBJECT-GROUP
OBJECTS {
dot11CurrentTxAntenna,
dot11DiversitySupportImplemented,
dot11CurrentRxAntenna }
STATUS deprecated
DESCRIPTION
"Attributes for Data Rates for IEEE 802.11."
::= { dot11Groups 8 }
dot11PhyTxPowerComplianceGroup OBJECT-GROUP
OBJECTS {
dot11NumberSupportedPowerLevelsImplemented,
dot11TxPowerLevel1,
dot11TxPowerLevel2,
dot11TxPowerLevel3,
dot11TxPowerLevel4,
dot11TxPowerLevel5,
dot11TxPowerLevel6,
dot11TxPowerLevel7,
dot11TxPowerLevel8,
dot11CurrentTxPowerLevel }
STATUS current
DESCRIPTION
"Attributes for Control and Management of transmit power."
::= { dot11Groups 9 }
dot11PhyFHSSComplianceGroup OBJECT-GROUP
OBJECTS {
dot11HopTime,
dot11CurrentChannelNumber,
dot11MaxDwellTime,
dot11CurrentDwellTime,
dot11CurrentSet,
dot11CurrentPattern,
dot11CurrentIndex }
STATUS deprecated
DESCRIPTION
"Superseded by dot11PhyFHSSComplianceGroup2.
Attributes that configure the Frequency Hopping for IEEE 802.11."
::= { dot11Groups 10 }
dot11PhyDSSSComplianceGroup OBJECT-GROUP
OBJECTS {
dot11CurrentChannel,
dot11CCAModeSupported,
dot11CurrentCCAMode,
dot11EDThreshold }
STATUS current
DESCRIPTION
"Attributes that configure the DSSS for IEEE 802.11."
::= { dot11Groups 11 }
dot11PhyIRComplianceGroup OBJECT-GROUP
OBJECTS {
dot11CCAWatchdogTimerMax,
dot11CCAWatchdogCountMax,
dot11CCAWatchdogTimerMin,
dot11CCAWatchdogCountMin }
STATUS current
DESCRIPTION
"Attributes that configure the baseband IR for IEEE 802.11."
::= { dot11Groups 12 }
dot11PhyRegDomainsSupportGroup OBJECT-GROUP
OBJECTS { dot11RegDomainsImplementedValue }
STATUS deprecated
DESCRIPTION
"Attributes that specify the supported Regulation Domains."
::= { dot11Groups 13 }
dot11PhyAntennasListGroup OBJECT-GROUP
OBJECTS {
dot11TxAntennaImplemented,
dot11RxAntennaImplemented,
dot11DiversitySelectionRxImplemented }
STATUS current
DESCRIPTION
"Attributes that specify the supported Regulation Domains."
::= { dot11Groups 14 }
dot11PhyRateGroup OBJECT-GROUP
OBJECTS {
dot11ImplementedDataRatesTxValue,
dot11ImplementedDataRatesRxValue }
STATUS current
DESCRIPTION
"Attributes for Data Rates for IEEE 802.11."
::= { dot11Groups 15 }
dot11CountersGroup OBJECT-GROUP
OBJECTS {
dot11TransmittedFragmentCount,
dot11GroupTransmittedFrameCount,
dot11FailedCount,
dot11ReceivedFragmentCount,
dot11GroupReceivedFrameCount,
dot11FCSErrorCount,
dot11WEPUndecryptableCount,
dot11TransmittedFrameCount }
STATUS deprecated
DESCRIPTION
"Superseded by dot11CountersGroup2.
Attributes from the dot11CountersGroup that are not described in the
dot11MACStatistics group. These objects are mandatory."
::= { dot11Groups 16 }
dot11NotificationGroup NOTIFICATION-GROUP
NOTIFICATIONS {
dot11Disassociate,
dot11Deauthenticate,
dot11AuthenticateFail,
dot11Associate,
dot11AssociateFailed,
dot11Reassociate,
dot11ReassociateFailed }
STATUS current
DESCRIPTION
"IEEE 802.11 notifications"
::= { dot11Groups 17 }
dot11SMTbase2 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation }
STATUS deprecated
DESCRIPTION
"Superseded by dot11SMTbase3.
The SMTbase2 object class provides the necessary support at the STA to
manage the processes in the STA such that the STA may work cooperatively
as a part of an IEEE 802.11 network."
::= { dot11Groups 18 }
dot11PhyOFDMComplianceGroup OBJECT-GROUP
OBJECTS {
dot11CurrentFrequency,
dot11TIThreshold,
dot11FrequencyBandsImplemented,
dot11ChannelStartingFactor }
STATUS deprecated
DESCRIPTION
"Superseded by dot11PhyOFDMComplianceGroup2.
Attributes that configure the OFDM for IEEE 802.11."
::= { dot11Groups 19 }
dot11SMTbase3 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString }
STATUS deprecated
DESCRIPTION
"Superseded by dot11SMTbase4.
The SMTbase3 object class provides the necessary support at the STA to
manage the processes in the STA such that the STA may work cooperatively
as a part of an IEEE 802.11 network, when the STA is capable of multidomain
operation. This object group should be implemented when the multidomain
capability option is implemented."
::= { dot11Groups 20 }
dot11MultiDomainCapabilityGroup OBJECT-GROUP
OBJECTS {
dot11FirstChannelNumber,
dot11NumberofChannels,
dot11MaximumTransmitPowerLevel }
STATUS current
DESCRIPTION
"The dot11MultiDomainCapabilityGroup object class provides the objects
necessary to manage the channels usable by a STA, when the multi-domain
capability option is implemented."
::= { dot11Groups 21 }
dot11PhyFHSSComplianceGroup2 OBJECT-GROUP
OBJECTS {
dot11HopTime,
dot11CurrentChannelNumber,
dot11MaxDwellTime,
dot11CurrentDwellTime,
dot11CurrentSet,
dot11CurrentPattern,
dot11CurrentIndex,
dot11EHCCPrimeRadix,
dot11EHCCNumberofChannelsFamilyIndex,
dot11EHCCCapabilityImplemented,
dot11EHCCCapabilityActivated,
dot11HopAlgorithmAdopted,
dot11RandomTableFlag,
dot11NumberofHoppingSets,
dot11HopModulus,
dot11HopOffset,
dot11RandomTableFieldNumber }
STATUS current
DESCRIPTION
"Attributes that configure the Frequency Hopping for IEEE 802.11 when
multi-domain capability option is implemented."
::= { dot11Groups 22 }
dot11PhyHRDSSSComplianceGroup OBJECT-GROUP
OBJECTS {
dot11CurrentChannel,
dot11CCAModeSupported,
dot11CurrentCCAMode,
dot11EDThreshold,
dot11ShortPreambleOptionImplemented,
dot11PBCCOptionImplemented,
dot11ChannelAgilityPresent,
dot11ChannelAgilityActivated,
dot11HRCCAModeImplemented }
STATUS current
DESCRIPTION
"Attributes that configure the HRDSSS for IEEE 802.11."
::= { dot11Groups 23 }
dot11PhyERPComplianceGroup OBJECT-GROUP
OBJECTS { dot11CurrentChannel,
dot11ShortPreambleOptionImplemented,
dot11ChannelAgilityPresent,
dot11ChannelAgilityActivated,
dot11DSSSOFDMOptionImplemented,
dot11DSSSOFDMOptionActivated,
dot11PBCCOptionImplemented,
dot11ERPPBCCOptionImplemented,
dot11ERPBCCOptionActivated,
dot11ShortSlotTimeOptionImplemented,
dot11ShortSlotTimeOptionActivated }
STATUS current
DESCRIPTION
"Attributes that configure the ERP."
::= { dot11Groups 24 }
dot11RSNAadditions OBJECT-GROUP
OBJECTS {
dot11RSNAActivated,
dot11RSNAPreauthenticationActivated }
STATUS current
DESCRIPTION
"This object class provides the objects from the IEEE 802.11 MIB required
to manage RSNA functionality. Note that additional objects for managing
this functionality are located in the IEEE 802.11 RSN MIB."
::= { dot11Groups 25 }
dot11SMTbase4 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID, dot11DesiredBSSType,
dot11OperationalRateSet,
dot11BeaconPeriod, dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11RSNAOptionImplemented }
STATUS deprecated
DESCRIPTION
"Superseded by dot11SMTbase5.
The SMTbase4 object class provides the necessary support at the IEEE STA
to manage the processes in the STA so that the STA may work cooperatively
as a part of an IEEE 802.11 network."
::= { dot11Groups 26 }
-- ********************************************************************
-- * Groups - units of conformance - RSN
-- ********************************************************************
dot11RSNBase OBJECT-GROUP
OBJECTS {
dot11RSNAConfigVersion,
dot11RSNAConfigPairwiseKeysImplemented,
dot11RSNAConfigGroupCipher,
dot11RSNAConfigGroupRekeyMethod,
dot11RSNAConfigGroupRekeyTime,
dot11RSNAConfigGroupRekeyPackets,
dot11RSNAConfigGroupRekeyStrict,
dot11RSNAConfigPSKValue,
dot11RSNAConfigPSKPassPhrase,
dot11RSNAConfigGroupUpdateCount,
dot11RSNAConfigPairwiseUpdateCount,
dot11RSNAConfigGroupCipherSize,
dot11RSNAConfigPairwiseCipherImplemented,
dot11RSNAConfigPairwiseCipherActivated,
dot11RSNAConfigPairwiseCipherSizeImplemented,
dot11RSNAConfigAuthenticationSuiteImplemented,
dot11RSNAConfigAuthenticationSuiteActivated,
dot11RSNAConfigNumberOfPTKSAReplayCountersImplemented,
dot11RSNAConfigSATimeout,
dot11RSNAConfigNumberOfGTKSAReplayCountersImplemented,
dot11RSNAAuthenticationSuiteSelected,
dot11RSNAPairwiseCipherSelected,
dot11RSNAGroupCipherSelected,
dot11RSNAPMKIDUsed,
dot11RSNAAuthenticationSuiteRequested,
dot11RSNAPairwiseCipherRequested,
dot11RSNAGroupCipherRequested,
dot11RSNATKIPCounterMeasuresInvoked,
dot11RSNA4WayHandshakeFailures,
dot11RSNAStatsSTAAddress,
dot11RSNAStatsVersion,
dot11RSNAStatsSelectedPairwiseCipher,
dot11RSNAStatsTKIPICVErrors,
dot11RSNAStatsTKIPLocalMICFailures,
dot11RSNAStatsTKIPRemoteMICFailures,
dot11RSNAStatsCCMPReplays,
dot11RSNAStatsCCMPDecryptErrors,
dot11RSNAStatsTKIPReplays,
dot11RSNAConfigSTKKeysImplemented,
dot11RSNAConfigSTKCipher,
dot11RSNAConfigSTKRekeyTime,
dot11RSNAConfigSMKUpdateCount,
dot11RSNAConfigSTKCipherSize,
dot11RSNAConfigNumberOfSTKSAReplayCountersImplemented,
dot11RSNAPairwiseSTKSelected,
dot11RSNAPreauthenticationImplemented,
dot11RSNASMKHandshakeFailures }
STATUS current
DESCRIPTION
"The dot11RSNBase object class provides the necessary support for managing
RSNA functionality in the STA."
::= { dot11Groups 27 }
dot11RSNPMKcachingGroup OBJECT-GROUP
OBJECTS {
dot11RSNAConfigPMKLifetime,
dot11RSNAConfigPMKReauthThreshold }
STATUS current
DESCRIPTION
"The dot11RSNPMKcachingGroup object class provides the necessary support
for managing PMK caching functionality in the STA"
::= { dot11Groups 28 }
dot11RSNSMKcachingGroup OBJECT-GROUP
OBJECTS {
dot11RSNAConfigSMKLifetime,
dot11RSNAConfigSMKReauthThreshold }
STATUS current
DESCRIPTION
"The dot11RSNSMKcachingGroup object class provides the necessary support
for managing SMK caching functionality in the STA."
::= { dot11Groups 29 }
dot11SMTbase5 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID, dot11DesiredBSSType,
dot11OperationalRateSet,
dot11BeaconPeriod, dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11SpectrumManagementImplemented,
dot11SpectrumManagementRequired,
dot11RSNAOptionImplemented,
dot11OperatingClassesImplemented,
dot11OperatingClassesRequired }
STATUS current
DESCRIPTION
"The SMTbase5 object class provides the necessary support at the STA to
manage the processes in the STA so that the STA may work cooperatively as
a part of an IEEE 802.11 network, when the STA is capable of multidomain
operation. This object group should be implemented when the multidomain
capability option is implemented."
::= { dot11Groups 30 }
dot11MACbase2 OBJECT-GROUP
OBJECTS {
dot11MACAddress,
dot11Address,
dot11GroupAddressesStatus,
dot11RTSThreshold,
dot11ShortRetryLimit,
dot11LongRetryLimit,
dot11FragmentationThreshold,
dot11MaxTransmitMSDULifetime,
dot11MaxReceiveLifetime,
dot11ManufacturerID,
dot11ProductID,
dot11CAPLimit,
dot11HCCWmin,
dot11HCCWmax,
dot11HCCAIFSN,
dot11ADDBAResponseTimeout,
dot11ADDTSResponseTimeout,
dot11ChannelUtilizationBeaconInterval,
dot11ScheduleTimeout,
dot11DLSResponseTimeout,
dot11QAPMissingAckRetryLimit,
dot11EDCAAveragingPeriod }
STATUS deprecated
DESCRIPTION
"Superseded by dot11MACbase3.
The MAC object class provides the necessary support for the access control,
generation, and verification of frame check sequences (FCSs), and
proper delivery of valid data to upper layers."
::= { dot11Groups 31 }
dot11CountersGroup2 OBJECT-GROUP
OBJECTS {
dot11TransmittedFragmentCount,
dot11GroupTransmittedFrameCount,
dot11FailedCount,
dot11ReceivedFragmentCount,
dot11GroupReceivedFrameCount,
dot11FCSErrorCount,
dot11WEPUndecryptableCount,
dot11TransmittedFrameCount,
dot11QosDiscardedFragmentCount,
dot11AssociatedStationCount,
dot11QosCFPollsReceivedCount,
dot11QosCFPollsUnusedCount,
dot11QosCFPollsUnusableCount }
STATUS deprecated
DESCRIPTION
"Superseded by dot11CountersGroup3.
Attributes from the dot11CountersGroup that are not described in the
dot11MACStatistics group. These objects are mandatory."
::= { dot11Groups 32 }
dot11Qosadditions OBJECT-GROUP
OBJECTS {
-- dot11EDCATable,
dot11EDCATableCWmin,
dot11EDCATableCWmax,
dot11EDCATableAIFSN,
dot11EDCATableTXOPLimit,
dot11EDCATableMSDULifetime,
dot11EDCATableMandatory,
-- dot11QAPEDCATable,
dot11QAPEDCATableCWmin,
dot11QAPEDCATableCWmax,
dot11QAPEDCATableAIFSN,
dot11QAPEDCATableTXOPLimit,
dot11QAPEDCATableMSDULifetime,
dot11QAPEDCATableMandatory,
-- dot11QosCountersTable
dot11QosTransmittedFragmentCount,
dot11QosFailedCount,
dot11QosRetryCount,
dot11QosMultipleRetryCount,
dot11QosFrameDuplicateCount,
dot11QosRTSSuccessCount,
dot11QosRTSFailureCount,
dot11QosACKFailureCount,
dot11QosReceivedFragmentCount,
dot11QosTransmittedFrameCount,
dot11QosDiscardedFrameCount,
dot11QosMPDUsReceivedCount,
dot11QosRetriesReceivedCount }
STATUS current
DESCRIPTION
"This object class provides the objects from the IEEE 802.11 MIB required
to manage QoS functionality."
::= { dot11Groups 33 }
dot11SMTbase6 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed }
STATUS deprecated
DESCRIPTION
"Superseded by dot11SMTbase7.
The SMTbase6 object class provides the necessary support at the STA to
manage the processes in the STA such that the STA may work cooperatively
as a part of an IEEE 802.11 network."
::= { dot11Groups 34 }
dot11PhyOFDMComplianceGroup2 OBJECT-GROUP
OBJECTS {
dot11CurrentFrequency,
dot11TIThreshold,
dot11FrequencyBandsImplemented,
dot11ChannelStartingFactor,
dot11FiveMHzOperationImplemented,
dot11TenMHzOperationImplemented,
dot11TwentyMHzOperationImplemented,
dot11PhyOFDMChannelWidth }
STATUS deprecated
DESCRIPTION
"Superseded by dot11PhyOFDMComplianceGroup3.
Attributes that configure the OFDM for IEEE 802.11."
::= { dot11Groups 35}
dot11SMTbase7 OBJECT-GROUP
OBJECTS{
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11SpectrumManagementImplemented,
dot11SpectrumManagementRequired,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11AssociateStation,
dot11AssociateID,
dot11AssociateFailStation,
dot11AssociateFailStatus,
dot11ReassociateStation,
dot11ReassociateID,
dot11ReassociateFailStation,
dot11ReassociateFailStatus,
dot11RadioMeasurementImplemented,
dot11RadioMeasurementActivated,
dot11RMMeasurementProbeDelay,
dot11RMMeasurementPilotPeriod,
dot11RMLinkMeasurementActivated,
dot11RMNeighborReportActivated,
dot11RMParallelMeasurementsActivated,
dot11RMRepeatedMeasurementsActivated,
dot11RMBeaconPassiveMeasurementActivated,
dot11RMBeaconActiveMeasurementActivated,
dot11RMBeaconTableMeasurementActivated,
dot11RMBeaconMeasurementReportingConditionsActivated,
dot11RMFrameMeasurementActivated,
dot11RMChannelLoadMeasurementActivated,
dot11RMNoiseHistogramMeasurementActivated,
dot11RMStatisticsMeasurementActivated,
dot11RMLCIMeasurementActivated,
dot11RMLCIAzimuthActivated,
dot11RMTransmitStreamCategoryMeasurementActivated,
dot11RMTriggeredTransmitStreamCategoryMeasurementActivated,
dot11RMAPChannelReportActivated,
dot11RMMIBActivated,
dot11RMMaxMeasurementDuration,
dot11RMNonOperatingChannelMaxMeasurementDuration,
dot11RMMeasurementPilotTransmissionInformationActivated,
dot11RMMeasurementPilotActivated,
dot11RMNeighborReportTSFOffsetActivated,
dot11RMRCPIMeasurementActivated,
dot11RMRSNIMeasurementActivated,
dot11RMBSSAverageAccessDelayActivated,
dot11RMBSSAvailableAdmissionCapacityActivated,
dot11RMAntennaInformationActivated}
STATUS deprecated
DESCRIPTION
"Superseded by dot11SMTbase8.
The SMTbase7 object class provides the necessary support at the STA to
manage the processes in the STA such that the STA may work cooperatively
as a part of an IEEE 802.11 net-work, when the STA is capable of multidomain
operation. This object group should be implemented when the multidomain
capability option is implemented."
::= { dot11Groups 36 }
dot11SMTRMRequest OBJECT-GROUP
OBJECTS {
dot11RMRqstRowStatus,
dot11RMRqstToken,
dot11RMRqstRepetitions,
dot11RMRqstIfIndex,
dot11RMRqstType,
dot11RMRqstTargetAdd,
dot11RMRqstTimeStamp,
dot11RMRqstChanNumber,
dot11RMRqstOperatingClass,
dot11RMRqstRndInterval,
dot11RMRqstDuration,
dot11RMRqstParallel,
dot11RMRqstEnable,
dot11RMRqstRequest,
dot11RMRqstReport,
dot11RMRqstDurationMandatory,
dot11RMRqstBeaconRqstMode,
dot11RMRqstBeaconRqstDetail,
dot11RMRqstFrameRqstType,
dot11RMRqstBssid,
dot11RMRqstSSID,
dot11RMRqstBeaconReportingCondition,
dot11RMRqstBeaconThresholdOffset,
dot11RMRqstSTAStatRqstGroupID,
dot11RMRqstLCIRqstSubject,
dot11RMRqstLCILatitudeResolution,
dot11RMRqstLCILongitudeResolution,
dot11RMRqstLCIAltitudeResolution,
dot11RMRqstLCIAzimuthType,
dot11RMRqstLCIAzimuthResolution,
dot11RMRqstPauseTime,
dot11RMRqstTransmitStreamPeerQSTAAddress,
dot11RMRqstTransmitStreamTrafficIdentifier,
dot11RMRqstTransmitStreamBin0Range,
dot11RMRqstTrigdQoSAverageCondition,
dot11RMRqstTrigdQoSConsecutiveCondition,
dot11RMRqstTrigdQoSDelayCondition,
dot11RMRqstTrigdQoSAverageThreshold,
dot11RMRqstTrigdQoSConsecutiveThreshold,
dot11RMRqstTrigdQoSDelayThresholdRange,
dot11RMRqstTrigdQoSDelayThreshold,
dot11RMRqstTrigdQoSMeasurementCount,
dot11RMRqstTrigdQoSTimeout,
dot11RMRqstChannelLoadReportingCondition,
dot11RMRqstChannelLoadReference,
dot11RMRqstNoiseHistogramReportingCondition,
dot11RMRqstAnpiReference,
dot11RMRqstAPChannelReport,
dot11RMRqstSTAStatPeerSTAAddress,
dot11RMRqstFrameTransmitterAddress,
dot11RMRqstVendorSpecific }
STATUS current
DESCRIPTION
"The SMTRMRequest package is a set of attributes that are present if the
STA supports the Radio Measurement service."
::= { dot11Groups 37 }
dot11SMTRMReport OBJECT-GROUP
OBJECTS {
dot11ChannelLoadRprtRqstToken,
dot11ChannelLoadRprtIfIndex,
dot11ChannelLoadMeasuringSTAAddr,
dot11ChannelLoadRprtChanNumber,
dot11ChannelLoadRprtOperatingClass,
dot11ChannelLoadRprtActualStartTime,
dot11ChannelLoadRprtMeasurementDuration,
dot11ChannelLoadRprtChannelLoad,
dot11ChannelLoadRprtVendorSpecific,
dot11ChannelLoadRprtMeasurementMode,
dot11NoiseHistogramRprtRqstToken,
dot11NoiseHistogramRprtIfIndex,
dot11NoiseHistogramMeasuringSTAAddr,
dot11NoiseHistogramRprtChanNumber,
dot11NoiseHistogramRprtOperatingClass,
dot11NoiseHistogramRprtActualStartTime,
dot11NoiseHistogramRprtMeasurementDuration,
dot11NoiseHistogramRprtAntennaID,
dot11NoiseHistogramRprtANPI,
dot11NoiseHistogramRprtIPIDensity0,
dot11NoiseHistogramRprtIPIDensity1,
dot11NoiseHistogramRprtIPIDensity2,
dot11NoiseHistogramRprtIPIDensity3,
dot11NoiseHistogramRprtIPIDensity4,
dot11NoiseHistogramRprtIPIDensity5,
dot11NoiseHistogramRprtIPIDensity6,
dot11NoiseHistogramRprtIPIDensity7,
dot11NoiseHistogramRprtIPIDensity8,
dot11NoiseHistogramRprtIPIDensity9,
dot11NoiseHistogramRprtIPIDensity10,
dot11NoiseHistogramRprtVendorSpecific,
dot11NoiseHistogramRprtMeasurementMode,
dot11BeaconRprtRqstToken,
dot11BeaconRprtIfIndex,
dot11BeaconMeasuringSTAAddr,
dot11BeaconRprtChanNumber,
dot11BeaconRprtOperatingClass,
dot11BeaconRprtActualStartTime,
dot11BeaconRprtMeasurementDuration,
dot11BeaconRprtPhyType,
dot11BeaconRprtReportedFrameType,
dot11BeaconRprtRCPI,
dot11BeaconRprtRSNI,
dot11BeaconRprtBSSID,
dot11BeaconRprtAntennaID,
dot11BeaconRprtParentTSF,
dot11BeaconRprtReportedFrameBody,
dot11BeaconRprtVendorSpecific,
dot11BeaconRprtMeasurementMode,
dot11FrameRprtIfIndex,
dot11FrameRprtRqstToken,
dot11FrameRprtChanNumber,
dot11FrameRprtOperatingClass,
dot11FrameRprtActualStartTime,
dot11FrameRprtMeasurementDuration,
dot11FrameRprtTransmitSTAAddress,
dot11FrameRprtBSSID,
dot11FrameRprtPhyType,
dot11FrameRprtAvgRCPI,
dot11FrameRprtLastRSNI,
dot11FrameRprtLastRCPI,
dot11FrameRprtAntennaID,
dot11FrameRprtNumberFrames,
dot11FrameRprtVendorSpecific,
dot11FrameRptMeasurementMode,
dot11STAStatisticsReportToken,
dot11STAStatisticsIfIndex,
dot11STAStatisticsSTAAddress,
dot11STAStatisticsMeasurementDuration,
dot11STAStatisticsGroupID,
dot11STAStatisticsTransmittedFragmentCount,
dot11STAStatisticsGroupTransmittedFrameCount,
dot11STAStatisticsFailedCount,
dot11STAStatisticsRetryCount,
dot11STAStatisticsMultipleRetryCount,
dot11STAStatisticsFrameDuplicateCount,
dot11STAStatisticsRTSSuccessCount,
dot11STAStatisticsRTSFailureCount,
dot11STAStatisticsACKFailureCount,
dot11STAStatisticsQosTransmittedFragmentCount,
dot11STAStatisticsQosFailedCount,
dot11STAStatisticsQosRetryCount,
dot11STAStatisticsQosMultipleRetryCount,
dot11STAStatisticsQosFrameDuplicateCount,
dot11STAStatisticsQosRTSSuccessCount,
dot11STAStatisticsQosRTSFailureCount,
dot11STAStatisticsQosACKFailureCount,
dot11STAStatisticsQosReceivedFragmentCount,
dot11STAStatisticsQosTransmittedFrameCount,
dot11STAStatisticsQosDiscardedFrameCount,
dot11STAStatisticsQosMPDUsReceivedCount,
dot11STAStatisticsQosRetriesReceivedCount,
dot11STAStatisticsReceivedFragmentCount,
dot11STAStatisticsGroupReceivedFrameCount,
dot11STAStatisticsFCSErrorCount,
dot11STAStatisticsTransmittedFrameCount,
dot11STAStatisticsAPAverageAccessDelay,
dot11STAStatisticsAverageAccessDelayBestEffort,
dot11STAStatisticsAverageAccessDelayBackground,
dot11STAStatisticsAverageAccessDelayVideo,
dot11STAStatisticsAverageAccessDelayVoice,
dot11STAStatisticsStationCount,
dot11STAStatisticsChannelUtilization,
dot11STAStatisticsVendorSpecific,
dot11STAStatisticsRprtMeasurementMode,
dot11LCIReportToken,
dot11LCIIfIndex,
dot11LCISTAAddress,
dot11LCILatitudeResolution,
dot11LCILatitudeInteger,
dot11LCILatitudeFraction,
dot11LCILongitudeResolution,
dot11LCILongitudeInteger,
dot11LCILongitudeFraction,
dot11LCIAltitudeType,
dot11LCIAltitudeResolution,
dot11LCIAltitudeInteger,
dot11LCIAltitudeFraction,
dot11LCIDatum,
dot11LCIAzimuthType,
dot11LCIAzimuthResolution,
dot11LCIAzimuth,
dot11LCIVendorSpecific,
dot11LCIRprtMeasurementMode,
dot11TransmitStreamRprtRqstToken,
dot11TransmitStreamRprtIfIndex,
dot11TransmitStreamMeasuringSTAAddr,
dot11TransmitStreamRprtActualStartTime,
dot11TransmitStreamRprtMeasurementDuration,
dot11TransmitStreamRprtPeerSTAAddress,
dot11TransmitStreamRprtTID,
dot11TransmitStreamRprtAverageQueueDelay,
dot11TransmitStreamRprtAverageTransmitDelay,
dot11TransmitStreamRprtTransmittedMSDUCount,
dot11TransmitStreamRprtMSDUDiscardedCount,
dot11TransmitStreamRprtMSDUFailedCount,
dot11TransmitStreamRprtMultipleRetryCount,
dot11TransmitStreamRprtCFPollsLostCount,
dot11TransmitStreamRprtBin0Range,
dot11TransmitStreamRprtDelayHistogram,
dot11TransmitStreamRprtReason,
dot11TransmitStreamRprtVendorSpecific,
dot11TransmitStreamRprtMeasurementMode }
STATUS current
DESCRIPTION
"The SMTRMReport package is a set of attributes that are present if the
STA supports the Radio Measurement service."
::= { dot11Groups 38 }
dot11SMTRMConfig OBJECT-GROUP
OBJECTS {
dot11APChannelReportIfIndex,
dot11APChannelReportOperatingClass,
dot11APChannelReportChannelList,
dot11RMNeighborReportIfIndex,
dot11RMNeighborReportBSSID,
dot11RMNeighborReportAPReachability,
dot11RMNeighborReportSecurity,
dot11RMNeighborReportCapSpectrumMgmt,
dot11RMNeighborReportCapQoS,
dot11RMNeighborReportCapAPSD,
dot11RMNeighborReportCapRM,
dot11RMNeighborReportCapDelayBlockAck,
dot11RMNeighborReportCapImmediateBlockAck,
dot11RMNeighborReportKeyScope,
dot11RMNeighborReportChannelNumber,
dot11RMNeighborReportOperatingClass,
dot11RMNeighborReportPhyType,
dot11RMNeighborReportNeighborTSFInfo,
dot11RMNeighborReportPilotInterval,
dot11RMNeighborReportPilotMultipleBSSID,
dot11RMNeighborReportRMEnabledCapabilities,
dot11RMNeighborReportVendorSpecific,
dot11RMNeighborReportRowStatus,
dot11RMNeighborReportCapHT,
dot11RMNeighborReportHTLDPCCodingCap,
dot11RMNeighborReportHTSupportedChannelWidthSet,
dot11RMNeighborReportHTSMPowerSave,
dot11RMNeighborReportHTGreenfield,
dot11RMNeighborReportHTShortGIfor20MHz,
dot11RMNeighborReportHTShortGIfor40MHz,
dot11RMNeighborReportHTTxSTBC,
dot11RMNeighborReportHTRxSTBC,
dot11RMNeighborReportHTDelayedBlockAck,
dot11RMNeighborReportHTMaxAMSDULength,
dot11RMNeighborReportHTDSSCCKModein40MHz,
dot11RMNeighborReportHTFortyMHzIntolerant,
dot11RMNeighborReportHTLSIGTXOPProtectionSupport,
dot11RMNeighborReportHTMaxAMPDULengthExponent,
dot11RMNeighborReportHTMinMPDUStartSpacing,
dot11RMNeighborReportHTRxMCSBitMask,
dot11RMNeighborReportHTRxHighestSupportedDataRate,
dot11RMNeighborReportHTTxMCSSetDefined,
dot11RMNeighborReportHTTxRxMCSSetNotEqual,
dot11RMNeighborReportHTTxMaxNumberSpatialStreamsSupported,
dot11RMNeighborReportHTTxUnequalModulationSupported,
dot11RMNeighborReportHTPCO,
dot11RMNeighborReportHTPCOTransitionTime,
dot11RMNeighborReportHTMCSFeedback,
dot11RMNeighborReportHTCSupport,
dot11RMNeighborReportHTRDResponder,
dot11RMNeighborReportHTImplictTransmitBeamformingReceivingCap,
dot11RMNeighborReportHTReceiveStaggeredSoundingCap,
dot11RMNeighborReportHTTransmitStaggeredSoundingCap,
dot11RMNeighborReportHTReceiveNDPCap,
dot11RMNeighborReportHTTransmitNDPCap,
dot11RMNeighborReportHTImplicitTransmitBeamformingCap,
dot11RMNeighborReportHTTransmitBeamformingCalibration,
dot11RMNeighborReportHTExplicitCSITransmitBeamformingCap,
dot11RMNeighborReportHTExplicitNonCompressedSteeringCap,
dot11RMNeighborReportHTExplicitCompressedSteeringCap,
dot11RMNeighborReportHTExplicitTransmitBeamformingFeedback,
dot11RMNbRprtHTExplicitNonCompressedBeamformingFeedbackCap,
dot11RMNeighborReportHTExplicitCompressedBeamformingFeedbackCap,
dot11RMNeighborReportHTTransmitBeamformingMinimalGrouping,
dot11RMNbRprtHTCSINumberofTxBeamformingAntennasSuppt,
dot11RMNbRprtHTNonCompressedSteeringNumofTxBmfmingAntennasSuppt,
dot11RMNbRprtHTCompressedSteeringNumberofTxBmfmingAntennasSuppt,
dot11RMNbRprtHTCSIMaxNumberofRowsTxBeamformingSuppt,
dot11RMNeighborReportHTTransmitBeamformingChannelEstimationCap,
dot11RMNeighborReportHTAntSelectionCap,
dot11RMNeighborReportHTExplicitCSIFeedbackBasedTxASELCap,
dot11RMNeighborReportHTAntIndicesFeedbackBasedTxASELCap,
dot11RMNeighborReportHTExplicitCSIFeedbackBasedCap,
dot11RMNeighborReportHTAntIndicesFeedbackCap,
dot11RMNeighborReportHTRxASELCap,
dot11RMNeighborReportHTTxSoundingPPDUsCap,
dot11RMNeighborReportHTInfoPrimaryChannel,
dot11RMNeighborReportHTInfoSecChannelOffset,
dot11RMNeighborReportHTInfoSTAChannelWidth,
dot11RMNeighborReportHTInfoRIFSMode,
dot11RMNeighborReportHTInfoProtection,
dot11RMNeighborReportHTInfoNonGreenfieldHTSTAsPresent,
dot11RMNeighborReportHTInfoOBSSNonHTSTAsPresent,
dot11RMNeighborReportHTInfoDualBeacon,
dot11RMNeighborReportHTInfoDualCTSProtection,
dot11RMNeighborReportHTInfoSTBCBeacon,
dot11RMNeighborReportHTInfoLSIGTXOPProtectionSup,
dot11RMNeighborReportHTInfoPCOActive,
dot11RMNeighborReportHTInfoPCOPhase,
dot11RMNeighborReportHTInfoBasicMCSSet,
dot11RMNeighborReportHTSecChannelOffset,
dot11RMNeighborReportExtCapPSMPSupport,
dot11RMNeighborReportExtCapSPSMPSup,
dot11RMNeighborReportExtCapServiceIntervalGranularity }
STATUS current
DESCRIPTION
"The SMTRMConfig package is a set of attributes that are present if the
STA supports the Radio Measurement service."
::= { dot11Groups 39 }
dot11FTComplianceGroup OBJECT-GROUP
OBJECTS {
-- Dot11FastBSSTransitionConfigEntry
dot11FastBSSTransitionActivated,
dot11FTMobilityDomainID,
dot11FTOverDSActivated,
dot11FTResourceRequestSupported,
dot11FTR0KeyHolderID,
dot11FTR0KeyLifetime,
dot11FTR1KeyHolderID,
dot11FTReassociationDeadline,
-- Dot11RMNeighborReportEntry
dot11RMNeighborReportMobilityDomain }
STATUS current
DESCRIPTION
"This object class provides the objects from the IEEE 802.11 MIB required
to manage fast BSS transition functionality. Note that additional objects
for managing this functionality are located in the dot11FastBSS TransitionConfigTable."
::= { dot11Groups 40}
dot11SMTbase8 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID, dot11DesiredBSSType,
dot11OperationalRateSet,
dot11BeaconPeriod, dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11SpectrumManagementImplemented,
dot11SpectrumManagementRequired,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11AssociateStation,
dot11AssociateID,
dot11AssociateFailStation,
dot11AssociateFailStatus,
dot11ReassociateStation,
dot11ReassociateID,
dot11ReassociateFailStation,
dot11ReassociateFailStatus,
dot11RadioMeasurementImplemented,
dot11RadioMeasurementActivated,
dot11RMMeasurementProbeDelay,
dot11RMMeasurementPilotPeriod,
dot11RMLinkMeasurementActivated,
dot11RMNeighborReportActivated,
dot11RMParallelMeasurementsActivated,
dot11RMRepeatedMeasurementsActivated,
dot11RMBeaconPassiveMeasurementActivated,
dot11RMBeaconActiveMeasurementActivated,
dot11RMBeaconTableMeasurementActivated,
dot11RMBeaconMeasurementReportingConditionsActivated,
dot11RMFrameMeasurementActivated,
dot11RMChannelLoadMeasurementActivated,
dot11RMNoiseHistogramMeasurementActivated,
dot11RMStatisticsMeasurementActivated,
dot11RMLCIMeasurementActivated,
dot11RMLCIAzimuthActivated,
dot11RMTransmitStreamCategoryMeasurementActivated,
dot11RMTriggeredTransmitStreamCategoryMeasurementActivated,
dot11RMAPChannelReportActivated,
dot11RMMIBActivated,
dot11RMMaxMeasurementDuration,
dot11RMNonOperatingChannelMaxMeasurementDuration,
dot11RMMeasurementPilotTransmissionInformationActivated,
dot11RMMeasurementPilotActivated,
dot11RMNeighborReportTSFOffsetActivated,
dot11RMRCPIMeasurementActivated,
dot11RMRSNIMeasurementActivated,
dot11RMBSSAverageAccessDelayActivated,
dot11RMBSSAvailableAdmissionCapacityActivated,
dot11RMAntennaInformationActivated,
dot11FastBSSTransitionImplemented }
STATUS deprecated
DESCRIPTION
"Superseded by dot11SMTbase9.
The SMTbase8 object class provides the necessary support at the STA to
manage the processes in the STA so that the STA may work cooperatively as
a part of an IEEE 802.11 network, when the STA is capable of multidomain
operation. This object group should be implemented when the multidomain
capability option is implemented."
::= { dot11Groups 41 }
dot11PhyOFDMComplianceGroup3 OBJECT-GROUP
OBJECTS {
dot11CurrentFrequency,
dot11FrequencyBandsImplemented,
dot11ChannelStartingFactor,
dot11FiveMHzOperationImplemented,
dot11TenMHzOperationImplemented,
dot11TwentyMHzOperationImplemented,
dot11PhyOFDMChannelWidth,
dot11OFDMCCAEDImplemented,
dot11OFDMCCAEDRequired,
dot11OFDMEDThreshold,
dot11STATransmitPowerClass,
dot11ACRType }
STATUS current
DESCRIPTION
"Attributes that configure the OFDM for IEEE 802.11."
::= { dot11Groups 42}
dot11SMTbase9 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID, dot11DesiredBSSType,
dot11OperationalRateSet,
dot11BeaconPeriod, dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11RadioMeasurementImplemented,
dot11RadioMeasurementActivated,
dot11FastBSSTransitionImplemented,
dot11LCIDSEImplemented,
dot11LCIDSERequired,
dot11DSERequired,
dot11ExtendedChannelSwitchActivated }
STATUS deprecated
DESCRIPTION
"Superseded by dot11SMTbase10.
The SMTbase9 object class provides the necessary support at the STA to
manage the processes in the STA such that the STA may work cooperatively
as a part of an IEEE 802.11 network, when the STA is capable of multidomain
operation. This object group should be implemented when the multidomain
capability option is implemented."
::= { dot11Groups 43 }
dot11PhyAntennaComplianceGroup2 OBJECT-GROUP
OBJECTS {
dot11CurrentTxAntenna,
dot11DiversitySupportImplemented,
dot11CurrentRxAntenna,
dot11AntennaSelectionOptionImplemented,
dot11TransmitExplicitCSIFeedbackASOptionImplemented,
dot11TransmitIndicesFeedbackASOptionImplemented,
dot11ExplicitCSIFeedbackASOptionImplemented,
dot11TransmitIndicesComputationASOptionImplemented,
dot11ReceiveAntennaSelectionOptionImplemented }
STATUS current
DESCRIPTION
"Attributes for Data Rates for IEEE 802.11."
::= { dot11Groups 44 }
dot11MACbase3 OBJECT-GROUP
OBJECTS {
dot11MACAddress,
dot11Address,
dot11GroupAddressesStatus,
dot11RTSThreshold,
dot11ShortRetryLimit,
dot11LongRetryLimit,
dot11FragmentationThreshold,
dot11MaxTransmitMSDULifetime,
dot11MaxReceiveLifetime,
dot11ManufacturerID,
dot11ProductID,
dot11CAPLimit,
dot11HCCWmin,
dot11HCCWmax,
dot11HCCAIFSN,
dot11ADDBAResponseTimeout,
dot11ADDTSResponseTimeout,
dot11ChannelUtilizationBeaconInterval,
dot11ScheduleTimeout,
dot11DLSResponseTimeout,
dot11QAPMissingAckRetryLimit,
dot11EDCAAveragingPeriod,
dot11HTProtection,
dot11RIFSMode,
dot11PSMPControlledAccess,
dot11ServiceIntervalGranularity,
dot11DualCTSProtection,
dot11LSIGTXOPFullProtectionActivated,
dot11NonGFEntitiesPresent, dot11PCOActivated,
dot11PCOFortyMaxDuration,
dot11PCOTwentyMaxDuration,
dot11PCOFortyMinDuration,
dot11PCOTwentyMinDuration }
STATUS current
DESCRIPTION
"The MAC object class provides the necessary support for the access control,
generation, and verification of frame check sequences (FCSs), and
proper delivery of valid data to upper layers."
::= { dot11Groups 45 }
dot11CountersGroup3 OBJECT-GROUP
OBJECTS {
dot11TransmittedFragmentCount,
dot11TransmittedFrameCount,
dot11FailedCount,
dot11ReceivedFragmentCount,
dot11GroupReceivedFrameCount,
dot11FCSErrorCount,
dot11WEPUndecryptableCount,
dot11TransmittedFrameCount,
dot11QosDiscardedFragmentCount,
dot11AssociatedStationCount,
dot11QosCFPollsReceivedCount,
dot11QosCFPollsUnusedCount,
dot11QosCFPollsUnusableCount,
dot11QosCFPollsLostCount,
dot11TransmittedAMSDUCount,
dot11FailedAMSDUCount,
dot11RetryAMSDUCount,
dot11MultipleRetryAMSDUCount,
dot11TransmittedOctetsInAMSDUCount,
dot11AMSDUAckFailureCount,
dot11ReceivedAMSDUCount,
dot11ReceivedOctetsInAMSDUCount,
dot11TransmittedAMPDUCount,
dot11TransmittedMPDUsInAMPDUCount,
dot11TransmittedOctetsInAMPDUCount,
dot11AMPDUReceivedCount,
dot11MPDUInReceivedAMPDUCount,
dot11ReceivedOctetsInAMPDUCount,
dot11AMPDUDelimiterCRCErrorCount,
dot11ImplicitBARFailureCount,
dot11ExplicitBARFailureCount,
dot11ChannelWidthSwitchCount,
dot11TwentyMHzFrameTransmittedCount,
dot11FortyMHzFrameTransmittedCount,
dot11TwentyMHzFrameReceivedCount,
dot11FortyMHzFrameReceivedCount,
dot11PSMPUTTGrantDuration,
dot11PSMPUTTUsedDuration,
dot11GrantedRDGUsedCount,
dot11GrantedRDGUnusedCount,
dot11TransmittedFramesInGrantedRDGCount,
dot11TransmittedOctetsInGrantedRDGCount,
dot11BeamformingFrameCount,
dot11DualCTSSuccessCount,
dot11DualCTSFailureCount,
dot11STBCCTSSuccessCount,
dot11STBCCTSFailureCount,
dot11nonSTBCCTSSuccessCount,
dot11nonSTBCCTSFailureCount,
dot11RTSLSIGSuccessCount,
dot11RTSLSIGFailureCount }
STATUS current
DESCRIPTION
"Attributes from the dot11CountersGroup that are not described in the
dot11MACStatistics group. These objects are mandatory."
::= { dot11Groups 46 }
dot11SMTbase10 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11AssociateStation,
dot11AssociateID,
dot11AssociateFailStation,
dot11AssociateFailStatus,
dot11ReassociateStation,
dot11ReassociateID,
dot11ReassociateFailStation,
dot11ReassociateFailStatus,
dot11RadioMeasurementImplemented,
dot11RadioMeasurementActivated,
dot11FastBSSTransitionImplemented,
dot11LCIDSEImplemented,
dot11LCIDSERequired,
dot11DSERequired,
dot11ExtendedChannelSwitchActivated,
dot11HighThroughputOptionImplemented,
dot11RSNAPBACRequired,
dot11PSMPOptionImplemented }
STATUS deprecated
DESCRIPTION
"Superceded by dot11SMTbase 11.
The SMTbase10 object class provides the necessary support at the STA to
manage the processes in the STA such that the STA may work cooperatively
as a part of an IEEE 802.11 network."
::= { dot11Groups 47 }
dot11PhyMCSGroup OBJECT-GROUP
OBJECTS {
dot11SupportedMCSTxValue,
dot11SupportedMCSRxValue }
STATUS current
DESCRIPTION
"Attributes for MCS for IEEE 802.11 HT."
::= { dot11Groups 48 }
dot11PhyHTComplianceGroup OBJECT-GROUP
OBJECTS {
dot11HighThroughputOptionImplemented,
dot11FortyMHzOperationImplemented,
dot11FortyMHzOperationActivated,
dot11FortyMHzIntolerant,
dot11FortyMHzOptionImplemented,
dot11CurrentPrimaryChannel,
dot11CurrentSecondaryChannel,
dot11HTGreenfieldOptionImplemented,
dot11HTGreenfieldOptionActivated,
dot11ShortGIOptionInTwentyImplemented,
dot11ShortGIOptionInTwentyActivated,
dot11ShortGIOptionInFortyImplemented,
dot11ShortGIOptionInFortyActivated,
dot11LDPCCodingOptionImplemented,
dot11LDPCCodingOptionActivated,
dot11TxSTBCOptionImplemented,
dot11TxSTBCOptionActivated,
dot11RxSTBCOptionImplemented,
dot11RxSTBCOptionActivated,
dot11BeamFormingOptionImplemented,
dot11BeamFormingOptionActivated,
dot11NumberOfSpatialStreamsImplemented,
dot11NumberOfSpatialStreamsActivated,
dot11HighestSupportedDataRate,
dot11TxMCSSetDefined,
dot11TxRxMCSSetNotEqual,
dot11TxMaximumNumberSpatialStreamsSupported,
dot11TxUnequalModulationSupported,
dot11TransmitSoundingPPDUOptionImplemented,
dot11NumberOfActiveRxAntennas }
STATUS current
DESCRIPTION
"Attributes that configure the HT for IEEE 802.11."
::= { dot11Groups 49 }
dot11HTMACAdditions OBJECT-GROUP
OBJECTS {
dot11HTOperationalMCSSet,
dot11MIMOPowerSave,
dot11NDelayedBlockAckOptionImplemented,
dot11MaxAMSDULength,
dot11STBCControlFrameOptionImplemented,
dot11LsigTxopProtectionOptionImplemented,
dot11MaxRxAMPDUFactor,
dot11MinimumMPDUStartSpacing,
dot11PCOOptionImplemented,
dot11TransitionTime,
dot11MCSFeedbackOptionImplemented,
dot11HTControlFieldSupported,
dot11RDResponderOptionImplemented,
dot11BSSWidthTriggerScanInterval,
dot11BSSWidthChannelTransitionDelayFactor,
dot11OBSSScanPassiveDwell,
dot11OBSSScanActiveDwell,
dot11OBSSScanPassiveTotalPerChannel,
dot11OBSSScanActiveTotalPerChannel,
dot112040BSSCoexistenceManagementSupport,
dot11OBSSScanActivityThreshold,
dot11SPPAMSDUCapable,
dot11SPPAMSDURequired }
STATUS current
DESCRIPTION
"Attributes that configure the HT for IEEE 802.11."
::= { dot11Groups 50 }
dot11TransmitBeamformingGroup OBJECT-GROUP
OBJECTS {
dot11ReceiveStaggerSoundingOptionImplemented,
dot11TransmitStaggerSoundingOptionImplemented,
dot11ReceiveNDPOptionImplemented,
dot11TransmitNDPOptionImplemented,
dot11ImplicitTransmitBeamformingOptionImplemented,
dot11CalibrationOptionImplemented,
dot11ExplicitCSITransmitBeamformingOptionImplemented,
dot11ExplicitNonCompressedBeamformingMatrixOptionImplemented,
dot11ExplicitTransmitBeamformingCSIFeedbackOptionImplemented,
dot11ExplicitNonCompressedBeamformingFeedbackOptionImplemented,
dot11ExplicitCompressedBeamformingFeedbackOptionImplemented,
dot11NumberBeamFormingCSISupportAntenna,
dot11NumberNonCompressedBeamformingMatrixSupportAntenna,
dot11NumberCompressedBeamformingMatrixSupportAntenna }
STATUS current
DESCRIPTION
"Attributes that configure the Beamforming for IEEE 802.11 HT."
::= { dot11Groups 51 }
dot11SMTbase11 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11SpectrumManagementImplemented,
dot11SpectrumManagementRequired,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11AssociateStation,
dot11AssociateID,
dot11AssociateFailStation,
dot11AssociateFailStatus,
dot11ReassociateStation,
dot11ReassociateID,
dot11ReassociateFailStation,
dot11ReassociateFailStatus,
dot11RadioMeasurementImplemented,
dot11RadioMeasurementActivated,
dot11RMMeasurementProbeDelay,
dot11RMMeasurementPilotPeriod,
dot11RMLinkMeasurementActivated,
dot11RMNeighborReportActivated,
dot11RMParallelMeasurementsActivated,
dot11RMRepeatedMeasurementsActivated,
dot11RMBeaconPassiveMeasurementActivated,
dot11RMBeaconActiveMeasurementActivated,
dot11RMBeaconTableMeasurementActivated,
dot11RMBeaconMeasurementReportingConditionsActivated,
dot11RMFrameMeasurementActivated,
dot11RMChannelLoadMeasurementActivated,
dot11RMNoiseHistogramMeasurementActivated,
dot11RMStatisticsMeasurementActivated,
dot11RMLCIMeasurementActivated,
dot11RMLCIAzimuthActivated,
dot11RMTransmitStreamCategoryMeasurementActivated,
dot11RMTriggeredTransmitStreamCategoryMeasurementActivated,
dot11RMAPChannelReportActivated,
dot11RMMIBActivated,
dot11RMMaxMeasurementDuration,
dot11RMNonOperatingChannelMaxMeasurementDuration,
dot11RMMeasurementPilotTransmissionInformationActivated,
dot11RMMeasurementPilotActivated,
dot11RMNeighborReportTSFOffsetActivated,
dot11RMRCPIMeasurementActivated,
dot11RMRSNIMeasurementActivated,
dot11RMBSSAverageAccessDelayActivated,
dot11RMBSSAvailableAdmissionCapacityActivated,
dot11FastBSSTransitionImplemented,
dot11LCIDSEImplemented,
dot11LCIDSERequired,
dot11DSERequired,
dot11ExtendedChannelSwitchActivated,
dot11HighThroughputOptionImplemented,
dot11WirelessManagementImplemented,
dot11RSNAPBACRequired,
dot11PSMPOptionImplemented }
STATUS deprecated
DESCRIPTION
"Superseded by dot11SMTbase12.
The SMTbase11 object class provides the necessary support at the STA to
manage the processes in the STA so that the STA may work cooperatively as
a part of an IEEE 802.11 network, when the STA is capable of multidomain
operation. This object group should be implemented when the multidomain
capability option is implemented."
::= { dot11Groups 53 }
dot11SMTWNMRequest OBJECT-GROUP
OBJECTS {
dot11WNMRqstRowStatus,
dot11WNMRqstToken,
dot11WNMRqstIfIndex,
dot11WNMRqstType,
dot11WNMRqstTargetAdd,
dot11WNMRqstTimeStamp,
dot11WNMRqstRndInterval,
dot11WNMRqstDuration,
dot11WNMRqstMcstGroup,
dot11WNMRqstMcstTrigCon,
dot11WNMRqstMcstTrigInactivityTimeout,
dot11WNMRqstMcstTrigReactDelay,
dot11WNMRqstLCRRqstSubject,
dot11WNMRqstLCRIntervalUnits,
dot11WNMRqstLCRServiceInterval,
dot11WNMRqstLIRRqstSubject,
dot11WNMRqstLIRIntervalUnits,
dot11WNMRqstLIRServiceInterval,
dot11WNMRqstEventToken,
dot11WNMRqstEventType,
dot11WNMRqstEventResponseLimit,
dot11WNMRqstEventTargetBssid,
dot11WNMRqstEventSourceBssid,
dot11WNMRqstEventTransitTimeThresh,
dot11WNMRqstEventTransitMatchValue,
dot11WNMRqstEventFreqTransitCountThresh,
dot11WNMRqstEventFreqTransitInterval,
dot11WNMRqstEventRsnaAuthType,
dot11WNMRqstEapType,
dot11WNMRqstEapVendorId,
dot11WNMRqstEapVendorType,
dot11WNMRqstEventRsnaMatchValue,
dot11WNMRqstEventPeerMacAddress,
dot11WNMRqstOperatingClass,
dot11WNMRqstChanNumber,
dot11WNMRqstDiagToken,
dot11WNMRqstDiagType,
dot11WNMRqstDiagTimeout,
dot11WNMRqstDiagBssid,
dot11WNMRqstDiagProfileId,
dot11WNMRqstDiagCredentials,
dot11WNMRqstLocConfigLocIndParams,
dot11WNMRqstLocConfigChanList,
dot11WNMRqstLocConfigBcastRate,
dot11WNMRqstLocConfigOptions,
dot11WNMRqstBssTransitQueryReason,
dot11WNMRqstBssTransitReqMode,
dot11WNMRqstBssTransitDisocTimer,
dot11WNMRqstBssTransitSessInfoURL,
dot11WNMRqstBssTransitCandidateList,
dot11WNMRqstColocInterfAutoEnable,
dot11WNMRqstColocInterfRptTimeout,
dot11WNMRqstVendorSpecific }
STATUS current
DESCRIPTION
"The SMTWNMRequest package is a set of attributes that shall be present if
the STA supports the WNM service."
::= { dot11Groups 54 }
dot11SMTWNMReport OBJECT-GROUP
OBJECTS {
dot11WNMVendorSpecificRprtRqstToken,
dot11WNMVendorSpecificRprtIfIndex,
dot11WNMVendorSpecificRprtContent,
dot11WNMMulticastDiagnosticRprtRqstToken,
dot11WNMMulticastDiagnosticRprtIfIndex,
dot11WNMMulticastDiagnosticRprtMeasurementTime,
dot11WNMMulticastDiagnosticRprtDuration,
dot11WNMMulticastDiagnosticRprtMcstGroup,
dot11WNMMulticastDiagnosticRprtReason,
dot11WNMMulticastDiagnosticRprtRcvdMsduCount,
dot11WNMMulticastDiagnosticRprtFirstSeqNumber,
dot11WNMMulticastDiagnosticRprtLastSeqNumber,
dot11WNMMulticastDiagnosticRprtMcstRate,
dot11WNMLocationCivicRprtRqstToken,
dot11WNMLocationCivicRprtIfIndex,
dot11WNMLocationCivicRprtCivicLocation,
dot11WNMLocationIdentifierRprtRqstToken,
dot11WNMLocationIdentifierRprtIfIndex,
dot11WNMLocationIdentifierRprtExpirationTSF,
dot11WNMLocationIdentifierRprtPublicIdUri,
dot11WNMEventTransitRprtRqstToken,
dot11WNMEventTransitRprtIfIndex,
dot11WNMEventTransitRprtEventStatus,
dot11WNMEventTransitRprtEventTSF,
dot11WNMEventTransitRprtUTCOffset,
dot11WNMEventTransitRprtTimeError,
dot11WNMEventTransitRprtSourceBssid,
dot11WNMEventTransitRprtTargetBssid,
dot11WNMEventTransitRprtTransitTime,
dot11WNMEventTransitRprtTransitReason,
dot11WNMEventTransitRprtTransitResult,
dot11WNMEventTransitRprtSourceRCPI,
dot11WNMEventTransitRprtSourceRSNI,
dot11WNMEventTransitRprtTargetRCPI,
dot11WNMEventTransitRprtTargetRSNI,
dot11WNMEventRsnaRprtRqstToken,
dot11WNMEventRsnaRprtIfIndex,
dot11WNMEventRsnaRprtEventStatus,
dot11WNMEventRsnaRprtEventTSF,
dot11WNMEventRsnaRprtUTCOffset,
dot11WNMEventRsnaRprtTimeError,
dot11WNMEventRsnaRprtTargetBssid,
dot11WNMEventRsnaRprtAuthType,
dot11WNMEventRsnaRprtEapMethod,
dot11WNMEventRsnaRprtResult,
dot11WNMEventRsnaRprtRsnElement,
dot11WNMEventPeerRprtRqstToken,
dot11WNMEventPeerRprtIfIndex,
dot11WNMEventPeerRprtEventStatus,
dot11WNMEventPeerRprtEventTSF,
dot11WNMEventPeerRprtUTCOffset,
dot11WNMEventPeerRprtTimeError,
dot11WNMEventPeerRprtPeerMacAddress,
dot11WNMEventPeerRprtOperatingClass,
dot11WNMEventPeerRprtChanNumber,
dot11WNMEventPeerRprtStaTxPower,
dot11WNMEventPeerRprtConnTime,
dot11WNMEventPeerRprtPeerStatus,
dot11WNMEventWNMLogRprtRqstToken,
dot11WNMEventWNMLogRprtIfIndex,
dot11WNMEventWNMLogRprtEventStatus,
dot11WNMEventWNMLogRprtEventTSF,
dot11WNMEventWNMLogRprtUTCOffset,
dot11WNMEventWNMLogRprtTimeError,
dot11WNMEventWNMLogRprtContent,
dot11WNMDiagMfrInfoRprtRqstToken,
dot11WNMDiagMfrInfoRprtIfIndex,
dot11WNMDiagMfrInfoRprtEventStatus,
dot11WNMDiagMfrInfoRprtMfrOi,
dot11WNMDiagMfrInfoRprtMfrIdString,
dot11WNMDiagMfrInfoRprtMfrModelString,
dot11WNMDiagMfrInfoRprtMfrSerialNumberString,
dot11WNMDiagMfrInfoRprtMfrFirmwareVersion,
dot11WNMDiagMfrInfoRprtMfrAntennaType,
dot11WNMDiagMfrInfoRprtCollocRadioType,
dot11WNMDiagMfrInfoRprtDeviceType,
dot11WNMDiagMfrInfoRprtCertificateID,
dot11WNMDiagConfigProfRprtRqstToken,
dot11WNMDiagConfigProfRprtIfIndex,
dot11WNMDiagConfigProfRprtEventStatus,
dot11WNMDiagConfigProfRprtProfileId,
dot11WNMDiagConfigProfRprtSupportedOperatingClasses,
dot11WNMDiagConfigProfRprtTxPowerMode,
dot11WNMDiagConfigProfRprtTxPowerLevels,
dot11WNMDiagConfigProfRprtCipherSuite,
dot11WNMDiagConfigProfRprtAkmSuite,
dot11WNMDiagConfigProfRprtEapType,
dot11WNMDiagConfigProfRprtEapVendorID,
dot11WNMDiagConfigProfRprtEapVendorType,
dot11WNMDiagConfigProfRprtCredentialType,
dot11WNMDiagConfigProfRprtSSID,
dot11WNMDiagConfigProfRprtPowerSaveMode,
dot11WNMDiagAssocRprtRqstToken,
dot11WNMDiagAssocRprtIfIndex,
dot11WNMDiagAssocRprtEventStatus,
dot11WNMDiagAssocRprtBssid,
dot11WNMDiagAssocRprtOperatingClass,
dot11WNMDiagAssocRprtChannelNumber,
dot11WNMDiagAssocRprtStatusCode,
dot11WNMDiag8021xAuthRprtRqstToken,
dot11WNMDiag8021xAuthRprtIfIndex,
dot11WNMDiag8021xAuthRprtEventStatus,
dot11WNMDiag8021xAuthRprtBssid,
dot11WNMDiag8021xAuthRprtOperatingClass,
dot11WNMDiag8021xAuthRprtChannelNumber,
dot11WNMDiag8021xAuthRprtEapType,
dot11WNMDiag8021xAuthRprtEapVendorID,
dot11WNMDiag8021xAuthRprtEapVendorType,
dot11WNMDiag8021xAuthRprtCredentialType,
dot11WNMDiag8021xAuthRprtStatusCode,
dot11WNMLocConfigRprtRqstToken,
dot11WNMLocConfigRprtIfIndex,
dot11WNMLocConfigRprtLocIndParams,
dot11WNMLocConfigRprtLocIndChanList,
dot11WNMLocConfigRprtLocIndBcastRate,
dot11WNMLocConfigRprtLocIndOptions,
dot11WNMLocConfigRprtStatusConfigSubelemId,
dot11WNMLocConfigRprtStatusResult,
dot11WNMLocConfigRprtVendorSpecificRprtContent,
dot11WNMBssTransitRprtRqstToken,
dot11WNMBssTransitRprtIfIndex,
dot11WNMBssTransitRprtStatusCode,
dot11WNMBssTransitRprtBSSTerminationDelay,
dot11WNMBssTransitRprtTargetBssid,
dot11WNMBssTransitRprtCandidateList,
dot11WNMColocInterfRprtRqstToken,
dot11WNMColocInterfRprtIfIndex,
dot11WNMColocInterfRprtPeriod,
dot11WNMColocInterfRprtInterfLevel,
dot11WNMColocInterfRprtInterfAccuracy,
dot11WNMColocInterfRprtInterfIndex,
dot11WNMColocInterfRprtInterfInterval,
dot11WNMColocInterfRprtInterfBurstLength,
dot11WNMColocInterfRprtInterfStartTime,
dot11WNMColocInterfRprtInterfCenterFreq,
dot11WNMColocInterfRprtInterfBandwidth }
STATUS current
DESCRIPTION
"The SMTWNMReport package is a set of attributes that shall be present if
the STA supports the WNM service."
::= { dot11Groups 55 }
dot11SMTbase12 OBJECT-GROUP
OBJECTS {
dot11MediumOccupancyLimit,
dot11CFPollable,
dot11CFPPeriod,
dot11CFPMaxDuration,
dot11AuthenticationResponseTimeOut,
dot11PrivacyOptionImplemented,
dot11PowerManagementMode,
dot11DesiredSSID,
dot11DesiredBSSType,
dot11OperationalRateSet,
dot11BeaconPeriod,
dot11DTIMPeriod,
dot11AssociationResponseTimeOut,
dot11DisassociateReason,
dot11DisassociateStation,
dot11DeauthenticateReason,
dot11DeauthenticateStation,
dot11AuthenticateFailStatus,
dot11AuthenticateFailStation,
dot11MultiDomainCapabilityImplemented,
dot11MultiDomainCapabilityActivated,
dot11CountryString,
dot11SpectrumManagementImplemented,
dot11SpectrumManagementRequired,
dot11RSNAOptionImplemented,
dot11OperatingClassesImplemented,
dot11OperatingClassesRequired,
dot11QosOptionImplemented,
dot11ImmediateBlockAckOptionImplemented,
dot11DelayedBlockAckOptionImplemented,
dot11DirectOptionImplemented,
dot11APSDOptionImplemented,
dot11QAckOptionImplemented,
dot11QBSSLoadImplemented,
dot11QueueRequestOptionImplemented,
dot11TXOPRequestOptionImplemented,
dot11MoreDataAckOptionImplemented,
dot11AssociateInNQBSS,
dot11DLSAllowedInQBSS,
dot11DLSAllowed,
dot11AssociateStation,
dot11AssociateID,
dot11AssociateFailStation,
dot11AssociateFailStatus,
dot11ReassociateStation,
dot11ReassociateID,
dot11ReassociateFailStation,
dot11ReassociateFailStatus,
dot11RadioMeasurementImplemented,
dot11RadioMeasurementActivated,
dot11RMMeasurementProbeDelay,
dot11RMMeasurementPilotPeriod,
dot11RMLinkMeasurementActivated,
dot11RMNeighborReportActivated,
dot11RMParallelMeasurementsActivated,
dot11RMRepeatedMeasurementsActivated,
dot11RMBeaconPassiveMeasurementActivated,
dot11RMBeaconActiveMeasurementActivated,
dot11RMBeaconTableMeasurementActivated,
dot11RMBeaconMeasurementReportingConditionsActivated,
dot11RMFrameMeasurementActivated,
dot11RMChannelLoadMeasurementActivated,
dot11RMNoiseHistogramMeasurementActivated,
dot11RMStatisticsMeasurementActivated,
dot11RMLCIMeasurementActivated,
dot11RMLCIAzimuthActivated,
dot11RMTransmitStreamCategoryMeasurementActivated,
dot11RMTriggeredTransmitStreamCategoryMeasurementActivated,
dot11RMAPChannelReportActivated,
dot11RMMIBActivated,
dot11RMMaxMeasurementDuration,
dot11RMNonOperatingChannelMaxMeasurementDuration,
dot11RMMeasurementPilotTransmissionInformationActivated,
dot11RMMeasurementPilotActivated,
dot11RMNeighborReportTSFOffsetActivated,
dot11RMRCPIMeasurementActivated,
dot11RMRSNIMeasurementActivated,
dot11RMBSSAverageAccessDelayActivated,
dot11RMBSSAvailableAdmissionCapacityActivated,
dot11FastBSSTransitionImplemented,
dot11LCIDSEImplemented,
dot11LCIDSERequired,
dot11DSERequired,
dot11ExtendedChannelSwitchActivated,
dot11HighThroughputOptionImplemented,
dot11WirelessManagementImplemented,
dot11MeshActivated,
dot11RSNAPBACRequired,
dot11PSMPOptionImplemented }
STATUS current
DESCRIPTION
"The SMTbase12 object class provides the necessary support at the STA to
manage the processes in the STA such that the STA may work cooperatively
as a part of an IEEE 802.11 network."
::= { dot11Groups 57 }
dot11OperatingClassesGroup OBJECT-GROUP
OBJECTS {
dot11OperatingClass,
dot11CoverageClass }
STATUS current
DESCRIPTION
"Attributes that configure the OFDM for IEEE 802.11 in many regulatory
domains."
::= { dot11Groups 58 }
dot11PhyOperationComplianceGroup2 OBJECT-GROUP
OBJECTS { dot11PHYType, dot11CurrentRegDomain }
STATUS current
DESCRIPTION
"PHY layer operations attributes."
::= { dot11Groups 59 }
dot11MeshComplianceGroup OBJECT-GROUP
OBJECTS {
-- dot11MeshSTAConfigTable
dot11MeshID,
dot11MeshNumberOfPeerings,
dot11MeshAcceptingAdditionalPeerings,
dot11MeshConnectedToMeshGate,
dot11MeshSecurityActivated,
dot11MeshActiveAuthenticationProtocol,
dot11MeshMaxRetries,
dot11MeshRetryTimeout,
dot11MeshConfirmTimeout,
dot11MeshHoldingTimeout,
dot11MeshActivePathSelectionProtocol,
dot11MeshActivePathSelectionMetric,
dot11MeshForwarding,
dot11MeshTTL,
dot11MeshGateAnnouncements,
dot11MeshActiveCongestionControlMode,
dot11MeshActiveSynchronizationMethod,
dot11MeshNbrOffsetMaxNeighbor,
dot11MBCAActivated,
dot11MCCAImplemented,
dot11MCCAActivated }
STATUS current
DESCRIPTION
"This object class provides the objects from the IEEE 802.11 MIB required
to manage mandatory mesh functionality. Note that additional objects for
managing mesh functionality are located in the dot11MeshOptionGroup,
dot11MeshHWMPComplianceGroup, and dot11PasswordAuthComplianceGroup."
::= { dot11Groups 56}
dot11MeshOptionGroup OBJECT-GROUP
OBJECTS {
-- dot11MeshSTAConfigTable
dot11MeshConfigGroupUpdateCount,
dot11MeshGateAnnouncementInterval,
dot11MeshBeaconTimingReportInterval,
dot11MeshBeaconTimingReportMaxNum,
dot11MeshDelayedBeaconTxInterval,
dot11MeshDelayedBeaconTxMaxDelay,
dot11MeshDelayedBeaconTxMinDelay,
dot11MeshAverageBeaconFrameDuration,
dot11MeshSTAMissingAckRetryLimit,
dot11MeshAwakeWindowDuration,
dot11MAFlimit,
dot11MCCAScanDuration,
dot11MCCAAdvertPeriodMax,
dot11MCCAMinTrackStates,
dot11MCCAMaxTrackStates,
dot11MCCAOPtimeout,
dot11MCCACWmin,
dot11MCCACWmax,
dot11MCCAAIFSN
}
STATUS current
DESCRIPTION
"This object class provides the objects from the IEEE 802.11 MIB required
to manage optional mesh functionality. Note that other objects for managing
mesh functionality are located in the dot11MeshComplianceGroup,
dot11MeshHWMPComplianceGroup, and dot11PasswordAuthComplianceGroup."
::= { dot11Groups 60 }
dot11MeshHWMPComplianceGroup OBJECT-GROUP
OBJECTS {
-- dot11MeshHWMPConfigTable
dot11MeshHWMPmaxPREQretries,
dot11MeshHWMPnetDiameter,
dot11MeshHWMPnetDiameterTraversalTime,
dot11MeshHWMPpreqMinInterval,
dot11MeshHWMPperrMinInterval,
dot11MeshHWMPactivePathToRootTimeout,
dot11MeshHWMPactivePathTimeout,
dot11MeshHWMProotMode,
dot11MeshHWMProotInterval,
dot11MeshHWMPrannInterval,
dot11MeshHWMPtargetOnly,
dot11MeshHWMPmaintenanceInterval,
dot11MeshHWMPconfirmationInterval }
STATUS current
DESCRIPTION
"This object class provides the objects from the IEEE 802.11 MIB required
to manage HWMP path selection functionality. Note that other objects for
managing mesh functionality are located in the dot11MeshComplianceGroup,
dot11MeshOptionGroup, and dot11PasswordAuthComplianceGroup."
::= { dot11Groups 61 }
dot11PasswordAuthComplianceGroup OBJECT-GROUP
OBJECTS {
-- dot11RSNAConfigTable
dot11RSNASAERetransPeriod,
dot11RSNASAEAntiCloggingThreshold,
dot11RSNASAESync,
-- dot11RSNAConfigPasswordValueTable
-- dot11RSNAConfigPasswordValueIndex,
dot11RSNAConfigPasswordCredential,
dot11RSNAConfigPasswordPeerMac,
-- dot11RSNAConfigDLCGroupTable
-- dot11RSNAConfigDLCGroupIndex,
dot11RSNAConfigDLCGroupIdentifier }
STATUS current
DESCRIPTION
"This object class provides the objects from the IEEE 802.11 MIB required
to manage password authentication. Note that other objects for managing
mesh functionality are located in the dot11MeshComplianceGroup,
dot11MeshOptionGroup, and dot11MeshHWMPComplianceGroup."
::= { dot11Groups 62 }
dot11SpectrumManagementGroup OBJECT-GROUP
OBJECTS {
-- Dot11SpectrumManagementEntry
-- dot11SpectrumManagementIndex,
dot11MitigationRequirement,
dot11ChannelSwitchTime,
dot11PowerCapabilityMaxImplemented,
dot11PowerCapabilityMinImplemented }
STATUS current
DESCRIPTION
"This object class provides the objects from the IEEE 802.11 MIB for spectrum
management."
::= { dot11Groups 72 }
dot11ProtectedManagementFrameGroup OBJECT-GROUP
OBJECTS {
-- Dot11StationConfigEntry
dot11RSNAProtectedManagementFramesActivated,
dot11RSNAUnprotectedManagementFramesAllowed,
dot11AssociationSAQueryMaximumTimeout,
dot11AssociationSAQueryRetryTimeout,
-- dot11RSNAStatsEntry
dot11RSNAStatsCMACICVErrors,
dot11RSNAStatsCMACReplays,
dot11RSNAStatsRobustMgmtCCMPReplays,
dot11RSNABIPMICErrors }
STATUS current
DESCRIPTION
"This object class provides the objects from the IEEE 802.11 MIB required
to operate protected management frame."
::= { dot11Groups 73 }
dot11LCIDSEGroup OBJECT-GROUP
OBJECTS {
-- Dot11LCIDSEEntry
-- dot11LCIDSEIndex,
dot11LCIDSEIfIndex,
dot11LCIDSECurrentOperatingClass,
dot11LCIDSELatitudeResolution,
dot11LCIDSELatitudeInteger,
dot11LCIDSELatitudeFraction,
dot11LCIDSELongitudeResolution,
dot11LCIDSELongitudeInteger,
dot11LCIDSELongitudeFraction,
dot11LCIDSEAltitudeType,
dot11LCIDSEAltitudeResolution,
dot11LCIDSEAltitudeInteger,
dot11LCIDSEAltitudeFraction,
dot11LCIDSEDatum,
dot11RegLocAgreement,
dot11RegLocDSE,
dot11DependentSTA,
dot11DependentEnablementIdentifier,
dot11DSEEnablementTimeLimit,
dot11DSEEnablementFailHoldTime,
dot11DSERenewalTime,
dot11DSETransmitDivisor }
STATUS current
DESCRIPTION
"This object class provides the objects from the IEEE 802.11 MIB required
to enable 3650-3700 MHz Operation in USA."
::= { dot11Groups 74 }
dot11TDLSComplianceGroup OBJECT-GROUP
OBJECTS {
-- Dot11StationConfigEntry
dot11TunneledDirectLinkSetupImplemented,
dot11TDLSPeerUAPSDBufferSTAActivated,
dot11TDLSPeerPSMActivated,
dot11TDLSPeerUAPSDIndicationWindow,
dot11TDLSChannelSwitchingActivated,
dot11TDLSPeerSTAMissingAckRetryLimit,
dot11TDLSResponseTimeout,
dot11OCBActivated,
dot11TDLSProbeDelay,
dot11TDLSDiscoveryRequestWindow,
dot11TDLSACDeterminationInterval }
STATUS current
DESCRIPTION
"This object class provides the objects from the IEEE 802.11 MIB required
to operate tunneled direct link setup."
::= { dot11Groups 75 }
-- **********************************************************************
-- * Compliance Statements
-- **********************************************************************
dot11Compliance MODULE-COMPLIANCE
STATUS current
DESCRIPTION
"The compliance statement for SNMPv2 entities that implement the IEEE
802.11 MIB."
MODULE -- this module
MANDATORY-GROUPS {
dot11SMTbase12,
dot11MACbase3,
dot11CountersGroup3,
dot11SmtAuthenticationAlgorithms,
dot11ResourceTypeID,
dot11PhyOperationComplianceGroup2 }
GROUP dot11PhyDSSSComplianceGroup
DESCRIPTION
"Implementation of this group is required when object dot11PHYType is
dsss.
This group is mutually exclusive to the following groups:
dot11PhyIRComplianceGroup
dot11PhyFHSSComplianceGroup2
dot11PhyOFDMComplianceGroup3
dot11PhyHRDSSSComplianceGroup
dot11PhyERPComplianceGroup
dot11PhyHTComplianceGroup"
GROUP dot11PhyIRComplianceGroup
DESCRIPTION
"Implementation of this group is required when object dot11PHYType is
irbaseband.
This group is mutually exclusive to the following groups:
dot11PhyFHSSComplianceGroup2
dot11PhyDSSSComplianceGroup
dot11PhyOFDMComplianceGroup3
dot11PhyHRDSSSComplianceGroup
dot11PhyERPComplianceGroup
dot11PhyHTComplianceGroup"
GROUP dot11PhyFHSSComplianceGroup2
DESCRIPTION
"Implementation of this group is required when object dot11PHYType is
fhss.
This group is mutually exclusive to the following groups:
dot11PhyIRComplianceGroup
dot11PhyDSSSComplianceGroup
dot11PhyOFDMComplianceGroup3
dot11PhyHRDSSSComplianceGroup
dot11PhyERPComplianceGroup
dot11PhyHTComplianceGroup"
GROUP dot11PhyOFDMComplianceGroup3
DESCRIPTION
"Implementation of this group is required when object dot11PHYType is
ofdm.
This group is mutually exclusive to the following groups:
dot11PhyIRComplianceGroup
dot11PhyFHSSComplianceGroup2
dot11PhyDSSSComplianceGroup
dot11PhyHRDSSSComplianceGroup
dot11PhyERPComplianceGroup
dot11PhyHTComplianceGroup"
GROUP dot11PhyHRDSSSComplianceGroup
DESCRIPTION
"Implementation of this group is required when object dot11PHYType is
hrdsss.
This group is mutually exclusive to the following groups:
dot11PhyIRComplianceGroup
dot11PhyFHSSComplianceGroup2
dot11PhyDSSSComplianceGroup
dot11PhyOFDMComplianceGroup3
dot11PhyERPComplianceGroup
dot11PhyHTComplianceGroup"
GROUP dot11PhyERPComplianceGroup
DESCRIPTION
"Implementation of this group is required when object dot11PHYType is ERP.
This group is mutually exclusive to the following groups:
dot11PhyIRComplianceGroup
dot11PhyFHSSComplianceGroup2
dot11PhyDSSSComplianceGroup
dot11PhyOFDMComplianceGroup3
dot11PhyHRDSSSComplianceGroup
dot11PhyHTComplianceGroup"
GROUP dot11PhyHTComplianceGroup
DESCRIPTION
"Implementation of this group is required when object dot11PHYType has the
value of ht.
This group is mutually exclusive to the following groups:
dot11PhyIRComplianceGroup
dot11PhyFHSSComplianceGroup2
dot11PhyDSSSComplianceGroup
dot11PhyOFDMComplianceGroup3
dot11PhyHRDSSSComplianceGroup
dot11PhyERPComplianceGroup"
GROUP dot11HTMACAdditions
DESCRIPTION
"The dot11HTMACAdditions group is optional."
GROUP dot11SMTprivacy
DESCRIPTION
"The dot11SMTprivacy group is optional."
GROUP dot11MACStatistics
DESCRIPTION
"The dot11MACStatistics group is optional."
GROUP dot11PhyTxPowerComplianceGroup
DESCRIPTION
"The dot11PhyTxPowerComplianceGroup group is optional."
GROUP dot11PhyRegDomainsSupportGroup
DESCRIPTION
"The dot11PhyRegDomainsSupportGroup group is optional."
GROUP dot11PhyAntennasListGroup
DESCRIPTION
"The dot11PhyAntennasListGroup group is optional."
GROUP dot11PhyRateGroup
DESCRIPTION
"The dot11PhyRateGroup group is optional."
GROUP dot11MultiDomainCapabilityGroup
DESCRIPTION
"The dot11MultiDomainCapabilityGroup group is optional."
GROUP dot11RSNAadditions
DESCRIPTION
"The dot11RSNAadditions group is optional."
GROUP dot11OperatingClassesGroup
DESCRIPTION
"The dot11OperatingClassesGroup group is optional."
GROUP dot11Qosadditions
DESCRIPTION
"The dot11Qosadditions group is optional."
GROUP dot11FTComplianceGroup
DESCRIPTION
"The dot11FTComplianceGroup group is optional."
GROUP dot11PhyAntennaComplianceGroup2
DESCRIPTION
"The dot11PhyAntennaComplianceGroup2 group is optional."
GROUP dot11PhyMCSGroup
DESCRIPTION
"The dot11PhyMCSGroup group is optional."
GROUP dot11TransmitBeamformingGroup
DESCRIPTION
"The dot11TransmitBeamformingGroup group is optional."
-- OPTIONAL-GROUPS {
-- dot11SMTprivacy,
-- dot11MACStatistics,
-- dot11PhyTxPowerComplianceGroup,
-- dot11PhyRegDomainsSupportGroup,
-- dot11PhyAntennasListGroup,
-- dot11PhyRateGroup,
-- dot11MultiDomainCapabilityGroup,
-- dot11PhyFHSSComplianceGroup2,
-- dot11RSNAadditions,
-- dot11OperatingClassesGroup,
-- dot11Qosadditions,
-- dot11RMCompliance,
-- dot11FTComplianceGroup,
-- dot11PhyAntennaComplianceGroup2,
-- dot11HTMACadditions,
-- dot11PhyMCSGroup,
-- dot11TransmitBeamformingGroup,
-- dot11WNMCompliance}
::= { dot11Compliances 1 }
-- ********************************************************************
-- * Compliance Statements - RSN
-- ********************************************************************
dot11RSNCompliance MODULE-COMPLIANCE
STATUS current
DESCRIPTION
"The compliance statement for SNMPv2 entities that implement the IEEE
802.11 RSN MIB."
MODULE -- this module
MANDATORY-GROUPS { dot11RSNBase }
-- OPTIONAL-GROUPS { dot11RSNPMKcachingGroup }
::= { dot11Compliances 2 }
-- ********************************************************************
-- * Compliance Statements - RM
-- ********************************************************************
dot11RMCompliance MODULE-COMPLIANCE
STATUS current
DESCRIPTION
"The compliance statement for SNMPv2 entities that implement the IEEE
802.11 MIB for Measurement Services."
MODULE -- this module
MANDATORY-GROUPS {
dot11SMTRMRequest,
dot11SMTRMReport,
dot11SMTRMConfig }
-- OPTIONAL-GROUPS { }
::= { dot11Compliances 3 }
-- ********************************************************************
-- * Compliance Statements - Mesh
-- ********************************************************************
dot11MeshCompliance MODULE-COMPLIANCE
STATUS current
DESCRIPTION
"The compliance statement for SNMPv2 entities that implement the IEEE
802.11 MIB for Mesh."
MODULE -- this module
MANDATORY-GROUPS {
dot11MeshComplianceGroup,
dot11MeshHWMPComplianceGroup,
dot11PasswordAuthComplianceGroup }
-- OPTIONAL-GROUPS { dot11MeshOptionGroup }
::= { dot11Compliances 4 }
-- ********************************************************************
-- * Compliance Statements - WNM
-- ********************************************************************
dot11WNMCompliance MODULE-COMPLIANCE
STATUS current
DESCRIPTION
" This object class provides the objects from the IEEE 802.11
MIB required to manage wireless network management
functionality. Note that additional objects for managing this
functionality are located in the IEEE 802.11 WNM MIB."
MODULE -- this module
MANDATORY-GROUPS { dot11SMTRMRequest, dot11SMTRMReport, dot11SMTRMConfig }
GROUP dot11SMTbase12
DESCRIPTION "At least the dot11WirelessManagementImplemented object is
required from dot11SMTbase12"
OBJECT dot11WirelessManagementImplemented
DESCRIPTION "Required object"
::= { dot11Compliances 5 }
-- ********************************************************************
-- * Compliance Statements - Spectrum Management
-- ********************************************************************
dot11SpectrumManagementCompliance MODULE-COMPLIANCE
STATUS current
DESCRIPTION
"This object class provides the objects from the IEEE 802.11
MIB used to operate higher throughput."
MODULE -- this module
MANDATORY-GROUPS { dot11SpectrumManagementGroup }
-- OPTIONAL-GROUPS { }
::= { dot11Compliances 10 }
-- ********************************************************************
-- * Compliance Statements - Protected management frame
-- ********************************************************************
dot11ProtectedManagementFrameCompliance MODULE-COMPLIANCE
STATUS current
DESCRIPTION
"This object class provides the objects from the IEEE 802.11
MIB required to operate protected management frames."
MODULE -- this module
MANDATORY-GROUPS { dot11ProtectedManagementFrameGroup }
-- OPTIONAL-GROUPS { }
::= { dot11Compliances 11 }
-- ********************************************************************
-- * Compliance Statements - LCIDSE
-- ********************************************************************
dot11LCIDSECompliance MODULE-COMPLIANCE
STATUS current
DESCRIPTION
"This object class provides the objects from the IEEE 802.11
MIB required to enable 3650-3700 MHz Operation in USA."
MODULE -- this module
MANDATORY-GROUPS { dot11LCIDSEGroup }
-- OPTIONAL-GROUPS { }
::= { dot11Compliances 12 }
-- ********************************************************************
-- * Compliance Statements - TDLS
-- ********************************************************************
dot11TDLSCompliance MODULE-COMPLIANCE
STATUS current
DESCRIPTION
"This object class provides the objects from the IEEE 802.11
MIB required to manage tunnled direct link setup."
MODULE -- this module
MANDATORY-GROUPS { dot11TDLSComplianceGroup }
-- OPTIONAL-GROUPS { }
::= { dot11Compliances 13 }
-- **********************************************************************
-- * End of 802.11 MIB
-- **********************************************************************
END
