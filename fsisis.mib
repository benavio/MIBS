-- Copyright (C) 2006-2012 Aricent Group . All Rights Reserved

--******************************************************************************
-- $Id: fsisis.mib,v 1.29 2016/03/26 09:57:17 siva Exp $
--
-- Description: This file contains typedefs for various events logged by 
--              FutureISIS
--*****************************************************************************/

ISIS-MIB DEFINITIONS ::= BEGIN

     IMPORTS
         TEXTUAL-CONVENTION, DisplayString, RowStatus, TruthValue
             FROM SNMPv2-TC
         MODULE-IDENTITY, OBJECT-TYPE, OBJECT-IDENTITY, Integer32,NOTIFICATION-TYPE,
         enterprises, Unsigned32
             FROM SNMPv2-SMI
        InetAddressType, InetAddress, InetAddressPrefixLength
                FROM INET-ADDRESS-MIB;

    fsIsis MODULE-IDENTITY
         LAST-UPDATED "201209050000Z" 
         ORGANIZATION "ARICENT COMMUNICATIONS SOFTWARE"
         CONTACT-INFO "support@aricent.com" 
         
         DESCRIPTION
            " The MIB module for FutureIsis."
               REVISION "201209050000Z"
         DESCRIPTION
            " The MIB module for FutureIsis."
    ::={ enterprises futuresoftware(2076) 62 }

     fsIsisScl OBJECT IDENTIFIER ::= { fsIsis 1 }

     fsIsisExt OBJECT IDENTIFIER ::= { fsIsis 2 }

     fsIsisNotifications OBJECT IDENTIFIER ::= { fsIsis 3 }	
    

-- Type Definitions

    MetricType ::= TEXTUAL-CONVENTION
       STATUS       current
       DESCRIPTION
          "Class of metric at Level 2."
       SYNTAX           INTEGER
                           {
                            internal(1),
                            external(2)
                           }
    MetricStyle ::= TEXTUAL-CONVENTION
       STATUS       current
       DESCRIPTION
          "Do we use 1195 style Metrics or wide metrics."
       SYNTAX           INTEGER
                           {
                            narrow(1),
                            wide(2)
                           }

-- OBJECT IDENTIFIER definitions

    fsIsisExtSystem OBJECT-IDENTITY
        STATUS  current
        DESCRIPTION
            "The object describes Extension system wide attributes "
    ::= { fsIsisExt 1 }

    fsIsisExtCirc OBJECT-IDENTITY
        STATUS  current
        DESCRIPTION
            "The object describes Extension system attributes with one Circuit "
    ::= { fsIsisExt 2 }
    
   fsIsisExtSummAddr OBJECT-IDENTITY
       STATUS  current
       DESCRIPTION
         "The object describes Extension system attributes with Summary Address"
    ::= { fsIsisExt 3 }     

   fsIsisExtIPIf OBJECT-IDENTITY
        STATUS  current
        DESCRIPTION
            "The object describes Extension system attributes with IP Interface Address  "
    ::= { fsIsisExt 4 }

   fsIsisExtLog OBJECT-IDENTITY
        STATUS  current
        DESCRIPTION
         " The object describes Extension system with Log"
    ::= { fsIsisExt 5 }  

  fsIsisExtAdj OBJECT-IDENTITY
        STATUS  current
        DESCRIPTION
            "This object describes attributes associated with 
             with an ISIS adjacency."
    ::= { fsIsisExt 6 }


-- Future ISIS scalars definitions

     fsIsisMaxInstances      OBJECT-TYPE
         SYNTAX              Integer32 (1..255)
         MAX-ACCESS          read-write
         STATUS              obsolete
         DESCRIPTION
	    "This mib value is configured by updating the sizing Parameter 
	    (MAX_ISIS_INSTANCES)"
         ::= { fsIsisScl 1 }

     fsIsisMaxCircuits      OBJECT-TYPE
         SYNTAX              Integer32 (1..200000)
         MAX-ACCESS          read-write
         STATUS              obsolete
         DESCRIPTION
            "This mib value is configured by updating the sizing Parameter 
	    (MAX_ISIS_CIRCUITS)"
         ::= { fsIsisScl 2 }

     fsIsisMaxAreaAddrs      OBJECT-TYPE
         SYNTAX              Integer32 (1..20000)
         MAX-ACCESS          read-write
         STATUS              current
         DESCRIPTION
            "Specifies the maximum number of Area Addresses that can
            be present in the system."
         ::= { fsIsisScl 3 }

     fsIsisMaxAdjs      OBJECT-TYPE
         SYNTAX              Integer32 (1..200000)
         MAX-ACCESS          read-write
         STATUS              obsolete
         DESCRIPTION
	    "This mib value is configured by updating the sizing Parameter 
             (MAX_ISIS_ADJACENCIES)"
         ::= { fsIsisScl 4 }

     fsIsisMaxIPRAs     OBJECT-TYPE
         SYNTAX              Integer32 (1..200000)
         MAX-ACCESS          read-write
         STATUS              current
         DESCRIPTION
            "Specifies the maximum number of IP reachability entries that can
            be present in the system."
         ::= { fsIsisScl 5 }

     fsIsisMaxEvents      OBJECT-TYPE
         SYNTAX              Integer32 (1..200000)
         MAX-ACCESS          read-write
         STATUS              current
         DESCRIPTION
            "Specifies the maximum number of events that can be 
             logged by an Intermediate System."
         ::= { fsIsisScl 6 }

      fsIsisMaxSummAddr      OBJECT-TYPE
         SYNTAX              Integer32 (1..200000)
         MAX-ACCESS          read-write
         STATUS              current
         DESCRIPTION
            "Specifies the maximum number of Summarized IP Addresses that can
            be configured for the system."
         ::= { fsIsisScl 7 }

      fsIsisStatus     OBJECT-TYPE
         SYNTAX              INTEGER {
                              up (1),
                              shutdown(2), 
                              reset(3)
                             }
         MAX-ACCESS          read-write
         STATUS              current
         DESCRIPTION
           "Value 'UP' is by default whenever the system comes up. This value 
           is a read only value. The user cannot set the value to UP.
           The user can set the values only as RESET and 
           SHUTDOWN.
           If reset, it shuts down all the instances, if any, and releases
           memory back to system. It restarts the ISIS system with the set 
           of memory configurations available in 'gIsisMemConfigs'.
           If shutdown it releases the memory back to the system and 
           would not restart." 
         ::= { fsIsisScl 8 }

      fsIsisMaxLSPEntries     OBJECT-TYPE
         SYNTAX              Integer32 (1..200000)
         MAX-ACCESS          read-write
         STATUS              current
         DESCRIPTION
           "Specifies the maximum number of Link State Packet(LSP) entries that a system can
            accomodate"
         ::= { fsIsisScl 9 }

     fsIsisMaxMAA      OBJECT-TYPE
         SYNTAX              Integer32 (1..20000)
         MAX-ACCESS          read-write
         STATUS              obsolete
         DESCRIPTION
	    "This mib value is configured by updating the sizing Parameter 
	     (MAX_ISIS_MANUAL_AREA_ADDRESSES)"
         ::= { fsIsisScl 10 }

     fsIsisFTStatus      OBJECT-TYPE
         SYNTAX              INTEGER
                             {
                                 enable (1),
                                 disable (2)
                             }    
         MAX-ACCESS          read-write
         STATUS              current
         DESCRIPTION
            "Specifies the Fault Tolerance Status of the system.
            It takes the values ENABLE or DISABLE
            for enabling or diabling the Fault Tolerance support to the
            Intermediate System"
         ::= { fsIsisScl 11 }

   fsIsisFTState         OBJECT-TYPE
         SYNTAX              INTEGER 
                             {
                                 ftEnable (1),
                                 ftDisable (2),
                                 ftOOS (3),
                                 ftStandBy (4),
                                 ftActive (5),
                                 ftLSUEnable (6),
                                 ftLSUDisable (7)
                             }
         MAX-ACCESS          read-only
         STATUS              current
         DESCRIPTION
             "This object gives the information about the Fault Tolerance
             State of the Intermediate System, if Fault Tolerance is enabled."
        ::= { fsIsisScl 12 }

   fsIsisFactor         OBJECT-TYPE
         SYNTAX              Integer32 (1..100)
         MAX-ACCESS          read-write
         STATUS              current
         DESCRIPTION
             "This object specifies the factor which is used for memory 
              allocation"
        ::= { fsIsisScl 13 }

   fsIsisMaxRoutes         OBJECT-TYPE
         SYNTAX              Integer32 (1..200000)
         MAX-ACCESS          read-write
         STATUS              obsolete
         DESCRIPTION
	     "This mib value is configured by updating the sizing Parameter 
	      (MAX_ISIS_SPT_NODES)"
        ::= { fsIsisScl 14 }
  
   fsIsisRestartState         OBJECT-TYPE
	SYNTAX              INTEGER 
			    {
			    running (1),
				reStarting (2),
				starting (3),
		        adjSeenRA (4),
			    adjSeenCsnp (5),	
			    spfWait (6),
			    spfDone (7),
				overloadBitSet (8)	
			    }
	MAX-ACCESS          read-only
	STATUS              current
	DESCRIPTION
		"Current state of ISIS Graceful Restart .Options include the following: running -
		Normal router, reStarting - Forwarding plane is preserved, Starting - Forwarding plane 
		not preserved, adjSeenRA - Request acknowledgement came for all circuits, adjSeenCsnp -
		Csnp received from all the circuits, spfWait - spf Triggered, spfDone - spf completed,
		overloadBitSet - router's own zeroth LSP is transmitted with overload bit set"  
	DEFVAL { running }
	::= { fsIsisScl 15 }

     fsIsisExtSysTable OBJECT-TYPE
         SYNTAX SEQUENCE OF FsIsisExtSysEntry
         MAX-ACCESS not-accessible
         STATUS current
         DESCRIPTION
             "The set of instances of the Integrated IS-IS protocol
             existing on the system."
     ::= { fsIsisExtSystem 1 }

     fsIsisExtSysEntry OBJECT-TYPE
         SYNTAX FsIsisExtSysEntry
         MAX-ACCESS not-accessible
         STATUS current
         DESCRIPTION
             "Each row defines information specific to a single
             instance of the protocol existing on the system."
         INDEX { fsIsisExtSysInstance }
     ::= { fsIsisExtSysTable 1 }

     FsIsisExtSysEntry ::=
         SEQUENCE {
             fsIsisExtSysInstance
                 Integer32, 
             fsIsisExtSysAuthSupp
                 INTEGER,
             fsIsisExtSysAreaAuthType
                 INTEGER,
             fsIsisExtSysDomainAuthType
                 INTEGER,
             fsIsisExtSysAreaTxPasswd
                 OCTET STRING,
             fsIsisExtSysDomainTxPasswd
                 OCTET STRING,
             fsIsisExtSysMinSPFSchTime
                 Integer32,
             fsIsisExtSysMaxSPFSchTime
                 Integer32,
             fsIsisExtSysMinLSPMark 
                 Integer32,
             fsIsisExtSysMaxLSPMark 
                 Integer32,
             fsIsisExtSysDelMetSupp
                 TruthValue,
             fsIsisExtSysErrMetSupp
                 TruthValue,
             fsIsisExtSysExpMetSupp
                 TruthValue,
             fsIsisExtSysActSysType 
                 Integer32,
             fsIsisExtSysActMPS
                 Integer32,
             fsIsisExtSysActMaxAA
                 Integer32,
             fsIsisExtSysActSysIDLen 
                 Integer32,
             fsIsisExtSysActSysID 
                 OCTET STRING,
             fsIsisExtSysActOrigL1LSPBufSize
                 Integer32,
             fsIsisExtSysActOrigL2LSPBufSize
                 Integer32,
             fsIsisExtSysRouterID
                 OCTET STRING,
             fsIsisExtSysCkts
                 Integer32,
             fsIsisExtSysActiveCkts
                 Integer32,
             fsIsisExtSysAdjs
                 Integer32,
             fsIsisExtSysOperState
                 Integer32,
             fsIsisExtSysDroppedPDUs
                 Integer32,
             fsIsisExtRestartSupport
                 INTEGER,
             fsIsisExtGRRestartTimeInterval
                 Integer32,
             fsIsisExtGRT2TimeIntervalLevel1
                 Integer32,
             fsIsisExtGRT2TimeIntervalLevel2
                 Integer32,
             fsIsisExtGRT1TimeInterval
                 Integer32,
             fsIsisExtGRT1RetryCount
                 Integer32,
             fsIsisExtGRMode
                 INTEGER,
             fsIsisExtRestartStatus
                 INTEGER,
             fsIsisExtRestartExitReason
                 INTEGER,
             fsIsisExtRestartReason
                 INTEGER,
             fsIsisExtHelperSupport
                 INTEGER,
             fsIsisExtHelperGraceTimeLimit
                 Integer32,
             fsIsisRRDAdminStatus
                 INTEGER,
             fsIsisRRDProtoMaskForEnable
                 Integer32,
             fsIsisRRDProtoMaskForDisable
                 Integer32,
             fsIsisRRDRouteMapName
                 DisplayString,
             fsIsisRRDImportLevel
                 INTEGER,
             fsIsisMultiTopologySupport
                 INTEGER,
             fsIsisExtSysBfdSupport
                 INTEGER,
             fsIsisExtSysBfdAllIfStatus
                 INTEGER,
             fsIsisDotCompliance
                 TruthValue,
             fsIsisExtSysDynHostNameSupport
                 INTEGER,
             fsIsisMetricStyle
                MetricStyle
         }


     fsIsisExtSysInstance OBJECT-TYPE
         SYNTAX Integer32 (0..10000)
         MAX-ACCESS not-accessible
         STATUS current
         DESCRIPTION
             "The unique identifier of the Integrated IS-IS instance
             to which this row corresponds. This object follows the
             index behaviour."
     ::= { fsIsisExtSysEntry 1 }

   fsIsisExtSysAuthSupp OBJECT-TYPE
         SYNTAX INTEGER {
                            txRxDisable (4),
                            txEnable (5),
                            rxEnable (6),
                            txRxEnable (7)
                        }
                            
         MAX-ACCESS read-create
         STATUS current
         DESCRIPTION
             "This Objects Enables/Disables the authentication on
             Transmit/Receive direction"
         DEFVAL { 4 }
     ::= { fsIsisExtSysEntry 2 }

    
   fsIsisExtSysAreaAuthType   OBJECT-TYPE
         SYNTAX INTEGER {
                          cleartextAuth (1),
                          md5Auth (2)
                        }
         MAX-ACCESS read-write
         STATUS current
         DESCRIPTION
             "This object specifies the type of authentication method to be used 
              for control packets destined within an area. Current implementation 
              supports Cleartext (simple password) and MD5(HMAC-MD5) authentication. "
     DEFVAL {cleartextAuth }
     ::= { fsIsisExtSysEntry 3 }

   fsIsisExtSysDomainAuthType   OBJECT-TYPE
         SYNTAX INTEGER {
                          cleartextAuth (1),
                          md5Auth (2)
                        }
         MAX-ACCESS read-write
         STATUS current
         DESCRIPTION
             "This object specifies the type of authentication method to be used 
              for control packets between area. Current implementation supports
              Cleartext (simple password) and MD5(HMAC-MD5) authentication. "
     DEFVAL {cleartextAuth }
     ::= { fsIsisExtSysEntry 4 }

   fsIsisExtSysAreaTxPasswd OBJECT-TYPE
         SYNTAX OCTET STRING (SIZE(0..16))
         MAX-ACCESS read-write
         STATUS current
         DESCRIPTION
             "This object specifies the Password/MD5 key to be used for authentication while
             transmitting Level 1 control PDUs. "
     ::= { fsIsisExtSysEntry 5 }

   fsIsisExtSysDomainTxPasswd OBJECT-TYPE
         SYNTAX OCTET STRING (SIZE(0..16))
         MAX-ACCESS read-write
         STATUS current
         DESCRIPTION
             "This object specifies the Password/MD5 key to be used for authentication while
             transmitting Level 2 control PDUs. "
     ::= { fsIsisExtSysEntry 6 }

   fsIsisExtSysMinSPFSchTime OBJECT-TYPE
         SYNTAX Integer32 (1..100)
         MAX-ACCESS read-write
         STATUS current
         DESCRIPTION
             "Specifies the Minimum time Interval in secs to be used between successive
             scheduling of Shortest Path Algorithm (SPF)."
     ::= { fsIsisExtSysEntry 7 } 

   fsIsisExtSysMaxSPFSchTime OBJECT-TYPE
         SYNTAX Integer32 (1..1000)
         MAX-ACCESS read-write
         STATUS current
         DESCRIPTION
             "Specifies the Maximum time interval in secs to be used between successive
             scheduling of SPF Algorithm"
     ::= { fsIsisExtSysEntry 8 } 
   
   fsIsisExtSysMinLSPMark OBJECT-TYPE
         SYNTAX Integer32 (1..100)
         MAX-ACCESS read-write
         STATUS current
         DESCRIPTION
            "Specifies the minimum number of LSP changes to occur before
            scheduling SPF Algorithm"
     ::= { fsIsisExtSysEntry 9} 

   fsIsisExtSysMaxLSPMark OBJECT-TYPE
         SYNTAX Integer32 (1..1000)
         MAX-ACCESS read-write
         STATUS current
         DESCRIPTION
            "Specifies the maximum number of LSP changes to occur before
            scheduling SPF Algorithm"
     ::= { fsIsisExtSysEntry 10 } 

   fsIsisExtSysDelMetSupp OBJECT-TYPE
         SYNTAX TruthValue
         MAX-ACCESS read-write
         STATUS current
         DESCRIPTION
             " Indicates the support of Delay metric "
     ::= { fsIsisExtSysEntry 11 } 

   fsIsisExtSysErrMetSupp OBJECT-TYPE
         SYNTAX TruthValue
         MAX-ACCESS read-write
         STATUS current
         DESCRIPTION
             " Indicates the support of error metric "
     ::= { fsIsisExtSysEntry 12 } 

   fsIsisExtSysExpMetSupp OBJECT-TYPE
         SYNTAX TruthValue
         MAX-ACCESS read-write
         STATUS current
         DESCRIPTION
             " Indicates the support of expense metric"
     ::= { fsIsisExtSysEntry 13 } 

   fsIsisExtSysActSysType OBJECT-TYPE
         SYNTAX Integer32 
         MAX-ACCESS read-only
         STATUS current
         DESCRIPTION
             "The system type of the ISIS Instance which is currently valid."
     ::= { fsIsisExtSysEntry 14 }

   fsIsisExtSysActMPS OBJECT-TYPE

         SYNTAX Integer32 
         MAX-ACCESS read-only
         STATUS current
         DESCRIPTION
             " The current Maximum path splits for this system"
     ::= { fsIsisExtSysEntry 15 }

   fsIsisExtSysActMaxAA OBJECT-TYPE
         SYNTAX Integer32 
         MAX-ACCESS read-only
         STATUS current
         DESCRIPTION
             " The current System Maximum Area addresses"
     ::= { fsIsisExtSysEntry 16 }

   fsIsisExtSysActSysIDLen OBJECT-TYPE
         SYNTAX Integer32 
         MAX-ACCESS read-only
         STATUS current
         DESCRIPTION
             " The current system Identifier length"
     ::= { fsIsisExtSysEntry 17 }

   fsIsisExtSysActSysID OBJECT-TYPE
         SYNTAX OCTET STRING
         MAX-ACCESS read-only
         STATUS current
         DESCRIPTION
             " The current system identifier"
      ::= { fsIsisExtSysEntry 18 }

   
   fsIsisExtSysActOrigL1LSPBufSize OBJECT-TYPE
         SYNTAX Integer32 
         MAX-ACCESS read-only
         STATUS current
         DESCRIPTION
             " The current L1 Lsp buffer size in bytes"
     ::= { fsIsisExtSysEntry 19 }

   fsIsisExtSysActOrigL2LSPBufSize OBJECT-TYPE
         SYNTAX Integer32 
         MAX-ACCESS read-only
         STATUS current
         DESCRIPTION
             " The current L2 Lsp buffer size in bytes"
     ::= { fsIsisExtSysEntry 20 }

   fsIsisExtSysRouterID   OBJECT-TYPE
         SYNTAX OCTET STRING 
         MAX-ACCESS read-write
         STATUS current
         DESCRIPTION
             "The IP Address of the ISIS Instance, which can be used for
             unnumbered interfaces."
     ::= { fsIsisExtSysEntry 21 }

   fsIsisExtSysCkts   OBJECT-TYPE
         SYNTAX Integer32 
         MAX-ACCESS read-only
         STATUS current
         DESCRIPTION
             "The number of circuits in this instance"
     ::= { fsIsisExtSysEntry 22 }

   fsIsisExtSysActiveCkts   OBJECT-TYPE
         SYNTAX Integer32 
         MAX-ACCESS read-only
         STATUS current
         DESCRIPTION
             " The number of Active circuits in this instance"
     ::= { fsIsisExtSysEntry 23 }

   fsIsisExtSysAdjs   OBJECT-TYPE
         SYNTAX Integer32 
         MAX-ACCESS read-only
         STATUS current
         DESCRIPTION
             " The number of adjacencies in this instance"
     ::= { fsIsisExtSysEntry 24 }

   fsIsisExtSysOperState   OBJECT-TYPE
         SYNTAX Integer32 
         MAX-ACCESS read-only
         STATUS current
         DESCRIPTION
             " The number of adjacencies in this instance"
     ::= { fsIsisExtSysEntry 25 }

   fsIsisExtSysDroppedPDUs  OBJECT-TYPE
         SYNTAX Integer32
         MAX-ACCESS read-only
         STATUS current
         DESCRIPTION
           " The number of PDU dropped by the system"
      ::= { fsIsisExtSysEntry 26 }

-- Future ISIS  Graceful restart definitions

  fsIsisExtRestartSupport         OBJECT-TYPE
	SYNTAX              INTEGER 
			    {
                            none (1),
                            plannedOnly (2),
                            plannedAndUnplanned (3)
			    }
	MAX-ACCESS          read-write
	STATUS              current
	DESCRIPTION
		"This object specifies the configuration support in the Router for 
                 supporting ISIS graceful restart. Options include: no restart support,
                 only planned restarts or both planned and unplanned restarts."
	DEFVAL { none }
	::= { fsIsisExtSysEntry 27 }

  fsIsisExtGRRestartTimeInterval         OBJECT-TYPE
         SYNTAX              Integer32 (1..65535)
         MAX-ACCESS          read-write
         STATUS              current
         DESCRIPTION
             "The Configured (T3) time defines the maximum time for supporting 
              Graceful Restart on a  Restarting Router( where the maximum range 
              denotes the max age of the LSP).This object is persistent and 
              when written, the entity should save the value to non-volatile storage."
        ::= { fsIsisExtSysEntry 28 }

  fsIsisExtGRT2TimeIntervalLevel1         OBJECT-TYPE
         SYNTAX              Integer32 (1..32767) 
         MAX-ACCESS          read-write
         STATUS              current
         DESCRIPTION
             "The configured T2 time interval defines the maximum wait 
              time for the synchronization of the Level 1 LSDB on a 
              restarting/starting router."
	DEFVAL { 60 }
        ::= { fsIsisExtSysEntry 29 }

  fsIsisExtGRT2TimeIntervalLevel2         OBJECT-TYPE
         SYNTAX              Integer32 (1..32767)
         MAX-ACCESS          read-write
         STATUS              current
         DESCRIPTION
             "The configured T2 time interval defines the maximum wait time 
              for the synchronization of the 
              Level 2 LSDB on a restarting/starting router."
	DEFVAL { 60 }
        ::= { fsIsisExtSysEntry 30 }


   fsIsisExtGRT1TimeInterval         OBJECT-TYPE
         SYNTAX              Integer32 (1..180)
         MAX-ACCESS          read-write
         STATUS              current
         DESCRIPTION
             "The configured T1 time-interval defines the maximum time for 
              sending Hellos with GraceTLVs on each interface of a restarting 
              router. The T1 time-interval is the maximum time for reception 
              of GR Acks and CSNPs from a Helping/Running Router."
	 DEFVAL { 3 }
              ::= { fsIsisExtSysEntry 31 }

    fsIsisExtGRT1RetryCount     OBJECT-TYPE
         SYNTAX              Integer32 (1..200) 
         MAX-ACCESS          read-write
         STATUS              current
         DESCRIPTION
             "Describes the number of times the restarting router will 
              resend the Graceful Restart TLV with RR bit set. The Grace TLV is 
              sent till Grace Acks, CSNPs are received from neighboring helping routers."
	 DEFVAL { 3 }
        ::= { fsIsisExtSysEntry 32 }

   fsIsisExtGRMode         OBJECT-TYPE
	SYNTAX              INTEGER 
			    {
			    none (1),	
			    restarter (2),
		        helper (3),
		        helperdown (4)
			    }
	MAX-ACCESS          read-only
	STATUS              current
	DESCRIPTION
		"Current Mode of ISIS graceful restart on this router.Option 
                 include : None (normal router),Restarter(acting as an restarter), 
                 Helper (acting as an helper)"
	DEFVAL { none }
	::= { fsIsisExtSysEntry 33 }

    fsIsisExtRestartStatus         OBJECT-TYPE
	SYNTAX              INTEGER 
			    {
			    none (1),
		            plannedRestart (2),
			    unplannedRestart (3)	
			    }
	MAX-ACCESS          read-only
	STATUS              current
	DESCRIPTION
		"Current status of ISIS Restart status.That is after 
                 restart the restarter should know whether it is in planned 
                 restart or unplanned restart or normal start."
	DEFVAL { none }
	::= { fsIsisExtSysEntry 34 }

   fsIsisExtRestartExitReason OBJECT-TYPE
       SYNTAX      INTEGER { none (1),           -- not attempted
                             inProgress (2),     -- restart in progress
                             completed (3),      -- successfully completed
                             timedOut (4),       -- timed out
                             topologyChanged (5) -- aborted due to topology
                                                 -- change.

                           }
       MAX-ACCESS  read-only
       STATUS      current
       DESCRIPTION
		       "Describes the outcome of the last attempt at a
           graceful restart. If the value is 'none', no restart
           has yet been attempted. If the value is 'inProgress',
           a restart attempt is currently underway."

       ::= {  fsIsisExtSysEntry 35 }

    fsIsisExtRestartReason OBJECT-TYPE
       SYNTAX      INTEGER { 
                            unknown (1),
                            softwareRestart (2),
                            swReloadUpgrade (3),
                            switchToRedundant(4)

                           }
       MAX-ACCESS  read-write
       STATUS      current
       DESCRIPTION
		       "The reason for last restart of the ISIS Router.
            Options include: unknown ( unplanned outage).Planned Restart 
            reasons could include the following - softwarerestart,
            swreloadupgrade, switchtoredundant."
       ::= {  fsIsisExtSysEntry 36 }

  fsIsisExtHelperSupport OBJECT-TYPE
       SYNTAX      INTEGER {
			    none (1),	
                            restart (2),
                            bothRestartAndStart (3)
                           }
       MAX-ACCESS  read-write
       STATUS      current
       DESCRIPTION
                       "The router's helper policy for neighboring ISIS Routers 
                       undergoing graceful restart.Options include the 
                       following : RestartingRouter (support for Restarting Routers 
		       that ensure forwarding plane preservation) and BothRestartAndStart 
		       (support for Restarting routers that support/donot 
                       support forwarding plane preservation)."
	DEFVAL { none }
       ::= {  fsIsisExtSysEntry 37 }

  fsIsisExtHelperGraceTimeLimit  OBJECT-TYPE
       SYNTAX      Integer32 (0 | 180..65535)
       MAX-ACCESS  read-write
       STATUS      current
       DESCRIPTION
           "Maximum configured interval for supporting graceful restart 
            in neighboring routers.Time is configured in seconds. 
            Value of 0 indicates that we are accepting the received
            grace time from restarting router."
       DEFVAL {0}
      ::= { fsIsisExtSysEntry 38 }

   fsIsisRRDAdminStatus         OBJECT-TYPE
       SYNTAX                   INTEGER {
                                    disable(0),
                                    enable(1)
                                }
       MAX-ACCESS               read-write
       STATUS                   current
       DESCRIPTION
       "This object controls redistribution of Direct, Static, OSPF, RIP, BGP
        routes into ISIS. If this object is set to enable, routes from protocols
        specified by fsIsisRRDProtoMaskForEnable will be imported into ISIS and
        the ISIS learnt routes will be distributed to other protocols. If this object 
        is set as disable, routes learned from protocols specified by
        fsIsisRRDProtoMaskForEnable will be removed from ISIS and no route will
        be either distributed to or imported from IGP and BGP." 
       DEFVAL { disable }
       ::= { fsIsisExtSysEntry 39 }

  fsIsisRRDProtoMaskForEnable       OBJECT-TYPE
       SYNTAX                       Integer32
       MAX-ACCESS                   read-write
       STATUS                       current
       DESCRIPTION
       "This object specifies the bit mask of source protocols from which routes are
       imported to ISIS. (LSB corresponds to Bit 0)

            Bit 1, if set, indicates that direct routes can be 
            redistributed into ISIS. (value = 2)

            Bit 2, if set, indicates that static routes can be 
            redistributed into ISIS. (value = 4)

            Bit 7, if set, indicates that routes from RIP can be 
            redistributed into  ISIS. (value = 128)

            Bit 12, if set, indicates that OSPF routes can be 
            redistributed into ISIS. (value = 4096)

            Bit 13, if set, indicates that BGP routes can be 
            redistributed into ISIS. (value = 8192)
       Other bits are reserved for future use."
       ::= { fsIsisExtSysEntry 40 }

   fsIsisRRDProtoMaskForDisable      OBJECT-TYPE
       SYNTAX                       Integer32
       MAX-ACCESS                       read-write
       STATUS                           current
       DESCRIPTION
       "This object disables the redistribution to ISIS by the bit mask of
        source protocols. (LSB corresponds to Bit 0)

            Bit 1, if set, indicates that direct routes cannot be 
            redistributed into ISIS. (value = 2)

            Bit 2, if set, indicates that static routes cannot be 
            redistributed into ISIS. (value = 4)

            Bit 7, if set, indicates that routes from RIP cannot be
            redistributed into ISIS. (value = 128)

            Bit 12, if set, indicates that OSPF routes cannot be 
            redistributed into ISIS. (value = 4096)

            Bit 13, if set, indicates that BGP routes cannot be 
            redistributed into ISIS. (value = 4096)

       Other bits are reserved for future use."
       ::= { fsIsisExtSysEntry 41 }
    
    fsIsisRRDRouteMapName              OBJECT-TYPE
        SYNTAX             DisplayString (SIZE (0..20))
        MAX-ACCESS         read-write
        STATUS             current
        DESCRIPTION        "This object specifies the route-map during redistribution of routes. 
                            Redistribution can be configured only for one route map. Another 
                            route map can be assigned only if the already assigned routemap 
                            is disabled. To change this object reset and configure the new value."
    ::=  { fsIsisExtSysEntry 42 }

    fsIsisRRDImportLevel              OBJECT-TYPE
        SYNTAX              INTEGER
                            {
                              level1(1),
                              level2(2),
                              level12(3)
                             }
        MAX-ACCESS         read-write
        STATUS             current
        DESCRIPTION        "The object specifies the Level in which the imported routes to be stored or flooded"
	DEFVAL { level2 }
    ::=  { fsIsisExtSysEntry 43 }

    fsIsisMultiTopologySupport  OBJECT-TYPE
        SYNTAX      INTEGER {
                                enable(1),
                                disable(2)
                            }
        MAX-ACCESS   read-write
        STATUS       current
        DESCRIPTION
            "This object sets the status of multi topology support for isis router"
        DEFVAL { disable }
       ::= { fsIsisExtSysEntry 44 }

    fsIsisExtSysBfdSupport  OBJECT-TYPE
        SYNTAX      INTEGER {
                                enable(1),
                                disable(2)
                            }
        MAX-ACCESS   read-write
        STATUS       current
        DESCRIPTION
            "This object is used to enable or disable BFD support for ISIS. By default,
             it is disabled."
        DEFVAL { disable }
       ::= { fsIsisExtSysEntry 45 }

    fsIsisExtSysBfdAllIfStatus  OBJECT-TYPE
        SYNTAX      INTEGER {
                                enable(1),
                                disable(2)
                            }
        MAX-ACCESS   read-write
        STATUS       current
        DESCRIPTION
            "This object enables/disables BFD on all interfaces for which 
             ISIS is enabled. By default, it is disabled. This object
             can be enabled only if fsIsisExtSysBfdSupport is enabled.
             Enabling this object will internally enable BFD for all the
             interfaces on which ISIS is enabled."
        DEFVAL { disable }
       ::= { fsIsisExtSysEntry 46 }

        fsIsisDotCompliance      OBJECT-TYPE
        SYNTAX       TruthValue
        MAX-ACCESS   read-write
        STATUS       current
        DESCRIPTION
            "This Object is to set the compliance format of the NET ID for ISIS in router.
             By default, the value of the MIB is False(colon Compliant).If set to true,
             then the NET ID format shall be displayed in DOT compliant"
        DEFVAL { false }
       ::= { fsIsisExtSysEntry 47 }

    fsIsisExtSysDynHostNameSupport  OBJECT-TYPE
        SYNTAX      INTEGER {
                                enable(1),
                                disable(2)
                            }
        MAX-ACCESS   read-write
        STATUS       current
        DESCRIPTION
            "This object is used to enable/disable Dynamic hostname support for ISIS. By default,
             it is disabled. If enabled, then the NET ID shall be displayed 
             with its symbolic name."
        REFERENCE
        "RFC 5301, Section 3"
        DEFVAL { disable }
       ::= { fsIsisExtSysEntry 48 }
       
fsIsisMetricStyle      OBJECT-TYPE
        SYNTAX              MetricStyle
        MAX-ACCESS          read-write
        STATUS              current
        DESCRIPTION
           "This object is used to set type of metric style used. 
            By default, Narrow metric style is set."
        DEFVAL { narrow }
       ::= { fsIsisExtSysEntry 49}

-- System Area Receive password table

   fsIsisExtSysAreaRxPasswdTable OBJECT-TYPE
         SYNTAX SEQUENCE OF FsIsisExtSysAreaRxPasswdEntry
         MAX-ACCESS not-accessible
         STATUS current
         DESCRIPTION
             "The set of Area receive passwords used for authenticating
              Level 1 LSPs, CSNPs and PSNPs "
     ::= { fsIsisExtSystem 2 }

   fsIsisExtSysAreaRxPasswdEntry OBJECT-TYPE
         SYNTAX FsIsisExtSysAreaRxPasswdEntry
         MAX-ACCESS not-accessible
         STATUS current
         DESCRIPTION
             "Each row defines information specific to a single
             instance of the protocol existing on the system."
         INDEX { fsIsisExtSysInstance, fsIsisExtSysAreaRxPasswd }
     ::= { fsIsisExtSysAreaRxPasswdTable 1 }

     FsIsisExtSysAreaRxPasswdEntry ::=
         SEQUENCE {
                 fsIsisExtSysAreaRxPasswd
                     OCTET STRING,
                 fsIsisExtSysAreaRxPasswdExistState
                     RowStatus
         }

   fsIsisExtSysAreaRxPasswd OBJECT-TYPE
         SYNTAX OCTET STRING (SIZE (0..16))
         MAX-ACCESS not-accessible
         STATUS current
         DESCRIPTION
             "Specifies the Password to be used for authenticating incoming
             Level 1 Control packets."
     ::= { fsIsisExtSysAreaRxPasswdEntry 1 }

   fsIsisExtSysAreaRxPasswdExistState OBJECT-TYPE
         SYNTAX   RowStatus
         MAX-ACCESS read-write
         STATUS current
         DESCRIPTION
             "The exist state for the recieve password entry "
     ::= { fsIsisExtSysAreaRxPasswdEntry 2 }

   fsIsisExtSysDomainRxPasswdTable OBJECT-TYPE
         SYNTAX SEQUENCE OF FsIsisExtSysDomainRxPasswdEntry
         MAX-ACCESS not-accessible
         STATUS current
         DESCRIPTION
             "The set of Domain receive passwords used for authenticating
              Level 1 LSPs, CSNPs and PSNPs "
     ::= { fsIsisExtSystem 3 }

   fsIsisExtSysDomainRxPasswdEntry OBJECT-TYPE
         SYNTAX FsIsisExtSysDomainRxPasswdEntry
         MAX-ACCESS not-accessible
         STATUS current
         DESCRIPTION
             "Each row defines information specific to a single
             instance of the protocol existing on the system."
         INDEX { fsIsisExtSysInstance, fsIsisExtSysDomainRxPassword }
     ::= { fsIsisExtSysDomainRxPasswdTable 1 }

     FsIsisExtSysDomainRxPasswdEntry ::=
         SEQUENCE {
                 fsIsisExtSysDomainRxPassword
                     OCTET STRING,
                 fsIsisExtSysDomainRxPasswdExistState 
                     RowStatus
         }

   fsIsisExtSysDomainRxPassword OBJECT-TYPE
         SYNTAX OCTET STRING (SIZE (0..16))
         MAX-ACCESS not-accessible
         STATUS current
         DESCRIPTION
             "Specifies the Password to be used for authenticating incoming
             Level 2 Control packets."
     ::= { fsIsisExtSysDomainRxPasswdEntry 1 }

   fsIsisExtSysDomainRxPasswdExistState OBJECT-TYPE
         SYNTAX   RowStatus
         MAX-ACCESS read-write
         STATUS current
         DESCRIPTION
             "The exist state for the recieve password 
              entry "
     ::= { fsIsisExtSysDomainRxPasswdEntry 2 }

-- Extended Summary address table

     fsIsisExtSummAddrTable OBJECT-TYPE
         SYNTAX SEQUENCE OF FsIsisExtSummAddrEntry
         MAX-ACCESS not-accessible
         STATUS current
         DESCRIPTION
             "The set of IP summary addresses to use in forming the
             contents of LSPs originated by this Intermediate System."
     ::= { fsIsisExtSummAddr 1 }


     fsIsisExtSummAddrEntry OBJECT-TYPE
         SYNTAX FsIsisExtSummAddrEntry
         MAX-ACCESS not-accessible
         STATUS current
         DESCRIPTION
             "Each entry contains one IP summary address."
         INDEX { fsIsisExtSysInstance,
                 fsIsisExtSummAddressType,
                 fsIsisExtSummAddress,
                 fsIsisExtSummAddrPrefixLen}
     ::= { fsIsisExtSummAddrTable 1 }

     FsIsisExtSummAddrEntry ::=
         SEQUENCE {
             fsIsisExtSummAddressType
                 InetAddressType,
             fsIsisExtSummAddress
                 InetAddress,
             fsIsisExtSummAddrPrefixLen
                 InetAddressPrefixLength,
             fsIsisExtSummAddrDelayMetric
                 Integer32,
             fsIsisExtSummAddrErrorMetric
                 Integer32,
             fsIsisExtSummAddrExpenseMetric
                 Integer32,
             fsIsisExtSummAddrFullMetric
                 Unsigned32
         }

     fsIsisExtSummAddressType OBJECT-TYPE
         SYNTAX InetAddressType
         MAX-ACCESS not-accessible
         STATUS current
         DESCRIPTION
             "The Type of IP address for this summary address.
              This object follows the index behaviour."
     ::= { fsIsisExtSummAddrEntry 1 }

     fsIsisExtSummAddress OBJECT-TYPE
         SYNTAX InetAddress (SIZE(4|16))
         MAX-ACCESS not-accessible
         STATUS current
         DESCRIPTION
             "The IP Address value for this summary address.
              This object follows the index behaviour."
     ::= { fsIsisExtSummAddrEntry 2 }

     fsIsisExtSummAddrPrefixLen OBJECT-TYPE
         SYNTAX InetAddressPrefixLength (0..128)
         MAX-ACCESS not-accessible
         STATUS current
         DESCRIPTION
             "The Length of the IP NetMask for this summary address."
     ::= { fsIsisExtSummAddrEntry 3 }

     fsIsisExtSummAddrDelayMetric OBJECT-TYPE
         SYNTAX Integer32 (0..63)
         MAX-ACCESS read-write
         STATUS current
         DESCRIPTION
             "The delay metric value to announce this summary
             address with in LSPs generated by this system. If the 
             Delay Metric is not enabled then this value becomes zero"
         DEFVAL { 0 }
     ::= { fsIsisExtSummAddrEntry 4 }

     fsIsisExtSummAddrErrorMetric OBJECT-TYPE
         SYNTAX Integer32 (0..63)
         MAX-ACCESS read-write
         STATUS current
         DESCRIPTION
             "The Error metric value to announce this summary
             address with in LSPs generated by this system. If the
             Error Metric is not enabled then this value becomes zero"
         DEFVAL { 0 }
     ::= { fsIsisExtSummAddrEntry 5 }

     fsIsisExtSummAddrExpenseMetric OBJECT-TYPE
         SYNTAX Integer32 (0..63)
         MAX-ACCESS read-write
         STATUS current
         DESCRIPTION
             "The Expense metric value to announce this summary
             address with in LSPs generated by this system. If the
             Expense Metric is not enabled then this value becomes zero"
         DEFVAL { 0 }
     ::= { fsIsisExtSummAddrEntry 6 }

     fsIsisExtSummAddrFullMetric OBJECT-TYPE
         SYNTAX Unsigned32 (0..4261412864)
         MAX-ACCESS read-write
         STATUS current
         DESCRIPTION
             "The full metric value to announce this summary
             address with in LSPs generated by this system. If the
             multi-topology is no enabled, this value is set to zero"
         DEFVAL { 20 }
     ::= { fsIsisExtSummAddrEntry 7 }

   fsIsisExtSysEventTable OBJECT-TYPE
         SYNTAX SEQUENCE OF FsIsisExtSysEventEntry
         MAX-ACCESS not-accessible
         STATUS current
         DESCRIPTION
             "The list of events recorded "
     ::= { fsIsisExtSystem 4 }

     fsIsisExtSysEventEntry   OBJECT-TYPE
         SYNTAX FsIsisExtSysEventEntry 
         MAX-ACCESS not-accessible
         STATUS current
         DESCRIPTION
             " "
         INDEX { fsIsisExtSysInstance, 
                 fsIsisExtSysEventIdx,
                 fsIsisExtSysEvent }
     ::= { fsIsisExtSysEventTable 1 }

     FsIsisExtSysEventEntry ::=
         SEQUENCE {
                 fsIsisExtSysEventIdx
                     Integer32,
                 fsIsisExtSysEvent
                     Integer32,
                 fsIsisExtSysEventStr
                     DisplayString
         }


   fsIsisExtSysEventIdx   OBJECT-TYPE
         SYNTAX Integer32 (1..1000)
         MAX-ACCESS not-accessible
         STATUS current
         DESCRIPTION
             "The unique event index"
     ::= { fsIsisExtSysEventEntry 1 }

   fsIsisExtSysEvent   OBJECT-TYPE
         SYNTAX Integer32 (1..1000)
         MAX-ACCESS not-accessible
         STATUS current
         DESCRIPTION
             " Specifies the type of the Event Logged"
     ::= { fsIsisExtSysEventEntry 2 }

      fsIsisExtSysEventStr   OBJECT-TYPE
         SYNTAX DisplayString
         MAX-ACCESS read-only
         STATUS current
         DESCRIPTION
             "The event message. For the Details of the mapping for Event Values and Event Types, refer
              to section 5.3 of Isisdd01.doc"
     ::= { fsIsisExtSysEventEntry 3 }

   fsIsisExtSysIdToSysNameMappingTable OBJECT-TYPE
         SYNTAX SEQUENCE OF FsIsisExtSysIdToSysNameMappingEntry
         MAX-ACCESS not-accessible
         STATUS current
         DESCRIPTION
             "The Table contains set of hostnames to System IDs mapping that
              are dynamically learnt from the ISIS link-state PDUs having 
              hostname TLV (137). The table shall be empty when the Dynamic 
              hostname support is disabled."
     ::= { fsIsisExtSystem 5 }

     fsIsisExtSysIdToSysNameMappingEntry   OBJECT-TYPE
         SYNTAX FsIsisExtSysIdToSysNameMappingEntry
         MAX-ACCESS not-accessible
         STATUS current
         DESCRIPTION
             "This object specifies each entry that tracks information about one hostname to system ID 
              mapping."
         INDEX { fsIsisExtSysRouterInstance,fsIsisExtSysRouterSysID } 
     ::= { fsIsisExtSysIdToSysNameMappingTable 1 }

     FsIsisExtSysIdToSysNameMappingEntry ::=
         SEQUENCE {
                 fsIsisExtSysRouterInstance
                     Integer32,
                 fsIsisExtSysRouterSysID
                     OCTET STRING,
                 fsIsisExtSysRouterHostName
                     OCTET STRING
         }

     fsIsisExtSysRouterInstance OBJECT-TYPE
         SYNTAX Integer32 (0..10000)
         MAX-ACCESS not-accessible
         STATUS current
         DESCRIPTION
             "This object specifies the unique identifier of the Integrated IS-IS instance
             to which this row corresponds. This object follows the
             index behaviour."
     ::= { fsIsisExtSysIdToSysNameMappingEntry 1 }

   fsIsisExtSysRouterSysID   OBJECT-TYPE
         SYNTAX OCTET STRING
         MAX-ACCESS not-accessible
         STATUS current
         DESCRIPTION
             "This object specifies the System ID of the Intermediate System."
     ::= { fsIsisExtSysIdToSysNameMappingEntry 2 }

   fsIsisExtSysRouterHostName   OBJECT-TYPE
         SYNTAX OCTET STRING(SIZE(0..255))
         MAX-ACCESS read-only
         STATUS current
         DESCRIPTION
             "This object specifies the hostname listed in the LSP, or a zero-length
             string if none."
     ::= { fsIsisExtSysIdToSysNameMappingEntry 3 }

-- The Circuit Group

-- The Circuit Group is current

-- The Circuit Table
-- Each broadcast or point-to-point interface on the system
-- corresponds to one entry in the Circuit table. There may be
-- many X.25 DA circuit entries in the Circuit table for an
-- X.25 interface.

     fsIsisExtCircTable OBJECT-TYPE
         SYNTAX SEQUENCE OF FsIsisExtCircEntry
         MAX-ACCESS not-accessible
         STATUS current
         DESCRIPTION
             "The table of circuits used by each instance of
             Integrated IS-IS on this system."
     ::= { fsIsisExtCirc 1 }

     fsIsisExtCircEntry OBJECT-TYPE
         SYNTAX FsIsisExtCircEntry
         MAX-ACCESS not-accessible
         STATUS current
         DESCRIPTION
             "An fsisisExtCircEntry exists for each circuit used by
             Integrated IS-IS on this system."
         INDEX { fsIsisExtSysInstance,
                 fsIsisExtCircIndex }
     ::= { fsIsisExtCircTable 1 }


     FsIsisExtCircEntry ::=
         SEQUENCE {
           fsIsisExtCircIndex
              Integer32,
           fsIsisExtCircIfStatus
              INTEGER,
           fsIsisExtCircTxEnable
              TruthValue,
           fsIsisExtCircRxEnable
             TruthValue,
           fsIsisExtCircTxISHs
             Integer32,
           fsIsisExtCircRxISHs
             Integer32,
           fsIsisExtCircSNPA
             OCTET STRING,
           fsIsisExtCircMTID
             Integer32,
           fsIsisExtCircBfdStatus
             INTEGER,
		   fsIsisExtCircExtendedCircID
		     Unsigned32
         }

    fsIsisExtCircIndex OBJECT-TYPE
         SYNTAX Integer32 (1..2000000000)
         MAX-ACCESS not-accessible
         STATUS current
         DESCRIPTION
            " The identifier of this circuit, unique within the 
             instance of the protocol " 
     ::= { fsIsisExtCircEntry 1 }

   fsIsisExtCircIfStatus OBJECT-TYPE
         SYNTAX       INTEGER
                     {
                      off(1),
                      on(2)
                     }
         MAX-ACCESS read-create
         STATUS current
         DESCRIPTION
             "The interface status of the circuit. If lower layers
              do not provide interface status information, manager has to
              set the value"
         DEFVAL { off}
     ::= { fsIsisExtCircEntry 2 }

   fsIsisExtCircTxEnable OBJECT-TYPE
         SYNTAX TruthValue
         MAX-ACCESS read-create
         STATUS current
         DESCRIPTION
             "If true transmission is enabled on the circuit "
         DEFVAL { true }
     ::= { fsIsisExtCircEntry 3 }

   fsIsisExtCircRxEnable OBJECT-TYPE
         SYNTAX TruthValue
         MAX-ACCESS read-create
         STATUS current
         DESCRIPTION
             "If true Reception is enabled on the circuit "
         DEFVAL { true }
     ::= { fsIsisExtCircEntry 4 }

   fsIsisExtCircTxISHs OBJECT-TYPE
         SYNTAX Integer32
         MAX-ACCESS read-only
         STATUS current
         DESCRIPTION
             " The Number of ISH Pdus Transmitted by this Circuit"
         DEFVAL { 0 }
     ::= { fsIsisExtCircEntry 5 }

   fsIsisExtCircRxISHs OBJECT-TYPE
         SYNTAX Integer32
         MAX-ACCESS read-only
         STATUS current
         DESCRIPTION
             " The Number of ISH Pdus Received by the Circuit"
         DEFVAL { 0 }
     ::= { fsIsisExtCircEntry 6 }

   fsIsisExtCircSNPA OBJECT-TYPE  
         SYNTAX  OCTET STRING (SIZE(6))
         MAX-ACCESS read-create
         STATUS current
         DESCRIPTION
           " The Circuit SNPA Address. It should be of length 6 Bytes"
     ::= { fsIsisExtCircEntry 7 }      

   fsIsisExtCircMTID OBJECT-TYPE
         SYNTAX Integer32
         MAX-ACCESS read-only
         STATUS current
         DESCRIPTION
            "The supported MT-IDS for the isis circuit entry are Bit 0 and Bit 2.
             Bit 0 indicates that supported MT ID is 0 i.e IPV4 (Value is 1) and 
             Bit 2 indicates that supported MT ID is 2 i.e IPV6 (Value is 4)"

      ::= { fsIsisExtCircEntry 8 }

   fsIsisExtCircBfdStatus OBJECT-TYPE
         SYNTAX INTEGER {
                            enable(1),
                            disable(2)
                        }
         MAX-ACCESS read-write
         STATUS current
         DESCRIPTION
           "This object enables/disables BFD on a particular interface for which
            ISIS is enabled. By default, it is disabled. This object
            can be enabled only if fsIsisExtSysBfdSupport is enabled. "
      ::= { fsIsisExtCircEntry 9 }

   fsIsisExtCircExtendedCircID OBJECT-TYPE
	  	SYNTAX Unsigned32
	  	MAX-ACCESS read-only
	  	STATUS current
	  	DESCRIPTION
	  		"This object specifies the value to be used as the extended circuit ID in
	  		3Way handshake.  This value is only used if
	  		isisCirc3WayEnabled is true and it must be unique
	  		across all circuits on this IS."
	  ::= { fsIsisExtCircEntry 10 }

-- Extended Circuit Level Table

     fsIsisExtCircLevelTable OBJECT-TYPE
         SYNTAX SEQUENCE OF FsIsisExtCircLevelEntry
         MAX-ACCESS not-accessible
         STATUS current
         DESCRIPTION
             "Level specific information about circuits used by IS-IS"
     ::= { fsIsisExtCirc 2 }

     fsIsisExtCircLevelEntry OBJECT-TYPE
         SYNTAX FsIsisExtCircLevelEntry
         MAX-ACCESS not-accessible
         STATUS current
         DESCRIPTION
             "An isisCircLevelEntry exists for each level on
              each circuit used by Integrated IS-IS on this system."
         INDEX { fsIsisExtSysInstance,
                 fsIsisExtCircIndex,
                 fsIsisExtCircLevelIndex }
     ::= { fsIsisExtCircLevelTable 1 }

     FsIsisExtCircLevelEntry ::=
         SEQUENCE {
             fsIsisExtCircLevelIndex
                 INTEGER,
             fsIsisExtCircLevelDelayMetric
                 Integer32,
             fsIsisExtCircLevelErrorMetric
                 Integer32,
             fsIsisExtCircLevelExpenseMetric
                 Integer32,
             fsIsisExtCircLevelTxPassword
                 OCTET STRING,
             fsIsisExtCircLevelWideMetric
                 Unsigned32,
	     fsIsisExtCircLevelAuthType
	         INTEGER
          }

     fsIsisExtCircLevelIndex OBJECT-TYPE
         SYNTAX INTEGER {
             level1IS (1),
             level2IS (2)
             }
         MAX-ACCESS not-accessible
         STATUS current
         DESCRIPTION
             "The circuit level index"
     ::= { fsIsisExtCircLevelEntry 1 }

     fsIsisExtCircLevelDelayMetric OBJECT-TYPE
         SYNTAX Integer32 (0..63)
         MAX-ACCESS read-create
         STATUS current
         DESCRIPTION
             
             "The delay metric value of this circuit for this
              level. If the Delay metric is not enabled this value becomes
              zero"
         DEFVAL { 0 }
     ::= { fsIsisExtCircLevelEntry 2 }

     fsIsisExtCircLevelErrorMetric OBJECT-TYPE
         SYNTAX Integer32 (0..63)
         MAX-ACCESS read-create
         STATUS current
         DESCRIPTION
             
             "The Error metric value of this circuit for this
              level. If the Error metric is not enabled this value becomes 
              zero"
         DEFVAL { 0 }
     ::= { fsIsisExtCircLevelEntry 3 }
     
     fsIsisExtCircLevelExpenseMetric OBJECT-TYPE
         SYNTAX Integer32 (0..63)
         MAX-ACCESS read-create
         STATUS current
         DESCRIPTION
             
             "The Expense metric value of this circuit for this
              level. If  Expense metric is not enabled this value
              becomes zero"
         DEFVAL { 0 }
     ::= { fsIsisExtCircLevelEntry 4 }


     fsIsisExtCircLevelTxPassword OBJECT-TYPE
         SYNTAX OCTET STRING (SIZE(0..100))
         MAX-ACCESS read-write
         STATUS current
         DESCRIPTION
             "This object specifies the Password/MD5 key to be used for authentication while
              transmitting Level-1/Level-2 Hello PDUs. "
     ::= { fsIsisExtCircLevelEntry 5 }

     fsIsisExtCircLevelWideMetric OBJECT-TYPE
         SYNTAX Unsigned32 (0..16777214)
         MAX-ACCESS read-create
         STATUS current
         DESCRIPTION

             "The wide metric value of this circuit for this
              level. If multi-topology support is not enabled
              this value is set to zero"
         DEFVAL { 10 }
     ::= { fsIsisExtCircLevelEntry 6 }

    fsIsisExtCircLevelAuthType OBJECT-TYPE
         SYNTAX INTEGER {
                          cleartextAuth (1),
                          md5Auth (2)
                        }
         MAX-ACCESS read-write
         STATUS current
         DESCRIPTION

            "This object specifies the type of authentication method to be used for
             Level-1/Level-2 Hello packets. Current implementation supports
             Cleartext (simple password) and MD5(HMAC-MD5) authentication. "
         DEFVAL { cleartextAuth }
     ::= { fsIsisExtCircLevelEntry 7 }


-- Extended IPRA Table     

     fsIsisExtIPRATable OBJECT-TYPE
         SYNTAX SEQUENCE OF FsIsisExtIPRAEntry
         MAX-ACCESS not-accessible
         STATUS current
         DESCRIPTION
             "Extension of IPRA table in standard mib."
     ::= { fsIsisExtCirc 3 }

     fsIsisExtIPRAEntry OBJECT-TYPE
         SYNTAX FsIsisExtIPRAEntry
         MAX-ACCESS not-accessible
         STATUS current
         DESCRIPTION
             "Each entry defines an IP Reachable Address to a network
              subnetwork or host."
         INDEX { fsIsisExtSysInstance,
                 fsIsisExtIPRAType,
                 fsIsisExtIPRAIndex }
     ::= { fsIsisExtIPRATable 1 }

     FsIsisExtIPRAEntry ::=
         SEQUENCE {
             fsIsisExtIPRAType
                 INTEGER,
             fsIsisExtIPRAIndex
                 Integer32,
             fsIsisExtIPRADelayMetric
                 Integer32,
             fsIsisExtIPRAErrorMetric
                 Integer32,
             fsIsisExtIPRAExpenseMetric
                 Integer32,
             fsIsisExtIPRADelayMetricType
                 INTEGER,
             fsIsisExtIPRAErrorMetricType
                 INTEGER,
             fsIsisExtIPRAExpenseMetricType
                 INTEGER,
             fsIsisExtIPRANextHopType
                 InetAddressType,
             fsIsisExtIPRANextHop
                 InetAddress,
             fsIsisExtIPRAFullMetric
                 Unsigned32
         }

     fsIsisExtIPRAType  OBJECT-TYPE
         SYNTAX   INTEGER
             {
                 manual (1),
                 automatic (2)
             }
         MAX-ACCESS not-accessible
         STATUS current
         DESCRIPTION
           "The type of the IP Reachable Address. Manual
            are created by manager, and automatic is learnt
            through other protocols"
     ::= { fsIsisExtIPRAEntry 1 }       
            
     fsIsisExtIPRAIndex OBJECT-TYPE
         SYNTAX Integer32 (1..2000000000)
         MAX-ACCESS not-accessible
         STATUS current
         DESCRIPTION
             "The circuit level index"
     ::= { fsIsisExtIPRAEntry 2 }

     fsIsisExtIPRADelayMetric OBJECT-TYPE
         SYNTAX Integer32 (0..63)
         MAX-ACCESS read-create
         STATUS current
         DESCRIPTION
             
             "The Delay metric value of this IPReachability address. If the
              delay metric is not enabled then this value becomes zero"
       	 DEFVAL { 0 }
     ::= { fsIsisExtIPRAEntry 3 }

     fsIsisExtIPRAErrorMetric OBJECT-TYPE
         SYNTAX Integer32 (0..63)
         MAX-ACCESS read-create
         STATUS current
         DESCRIPTION
             
             "The Error metric value of this IPReachability address. If the
              error metric is not enabled then this value becomes zero"
       	 DEFVAL { 0 }
     ::= { fsIsisExtIPRAEntry 4 }
     
     fsIsisExtIPRAExpenseMetric OBJECT-TYPE
         SYNTAX Integer32 (0..63)
         MAX-ACCESS read-create
         STATUS current
         DESCRIPTION
             
             "The Expense metric value of this IPReachability address. If the
              expense metric is not enabled then this value becomes zero"
       	 DEFVAL { 0 }
     ::= { fsIsisExtIPRAEntry 5 }


     fsIsisExtIPRADelayMetricType OBJECT-TYPE
         SYNTAX MetricType
         MAX-ACCESS read-create
         STATUS current
         DESCRIPTION
             
             "The delay metric value of this circuit for this
              level"
     ::= { fsIsisExtIPRAEntry 6 }

     fsIsisExtIPRAErrorMetricType OBJECT-TYPE
         SYNTAX MetricType
         MAX-ACCESS read-create
         STATUS current
         DESCRIPTION
             
             "The Error metric value of this circuit for this
              level"
     ::= { fsIsisExtIPRAEntry 7 }
     
     fsIsisExtIPRAExpenseMetricType OBJECT-TYPE
         SYNTAX MetricType
         MAX-ACCESS read-create
         STATUS current
         DESCRIPTION
             
             "The Expense metric value of this circuit for this
              level"
     ::= { fsIsisExtIPRAEntry 8 }

     fsIsisExtIPRANextHopType OBJECT-TYPE
         SYNTAX InetAddressType
         MAX-ACCESS read-create
         STATUS current
         DESCRIPTION
             "The Type of IP address for this nexthop address." 
     ::= { fsIsisExtIPRAEntry 9 }


     fsIsisExtIPRANextHop OBJECT-TYPE
         SYNTAX InetAddress (SIZE(4|16))
         MAX-ACCESS read-create
         STATUS current
         DESCRIPTION
             "The IP Address to which a PDU may be forwarded in
              order to reach the destination which matches this IP
              Reachable Address. This object follows the
              manualOrAutomatic behavior."
     ::= { fsIsisExtIPRAEntry 10 }

     fsIsisExtIPRAFullMetric OBJECT-TYPE
         SYNTAX Unsigned32 (0..4261412864)
         MAX-ACCESS read-create
         STATUS current
         DESCRIPTION

             "The full metric value of this IPReachability address. If the
              multi-topology is not enabled then this value is set to zero"
         DEFVAL { 20 }
     ::= { fsIsisExtIPRAEntry 11 }


-- Circuit level received PasswordTable     

     fsIsisExtCircLevelRxPasswordTable OBJECT-TYPE
         SYNTAX SEQUENCE OF FsIsisExtCircLevelRxPasswordEntry
         MAX-ACCESS not-accessible
         STATUS current
         DESCRIPTION
             "List of receive passwords of circuits used by IS-IS"
     ::= { fsIsisExtCirc 4 }

     fsIsisExtCircLevelRxPasswordEntry OBJECT-TYPE
         SYNTAX FsIsisExtCircLevelRxPasswordEntry
         MAX-ACCESS not-accessible
         STATUS current
         DESCRIPTION
             "An isisCircLevelEntry exists for each level on
              each circuit used by Integrated IS-IS on this system."
         INDEX { fsIsisExtSysInstance,
                 fsIsisExtCircIndex,
                 fsIsisExtCircLevelIndex,
                 fsIsisExtCircLevelRxPassword }
     ::= { fsIsisExtCircLevelRxPasswordTable 1 }

     FsIsisExtCircLevelRxPasswordEntry ::=
         SEQUENCE {
             fsIsisExtCircLevelRxPassword
                 OCTET STRING,
             fsIsisExtCircLevelRxPasswordExistState
                 RowStatus
          }

     fsIsisExtCircLevelRxPassword OBJECT-TYPE
         SYNTAX OCTET STRING (SIZE (0..100))
         MAX-ACCESS not-accessible
         STATUS current
         DESCRIPTION
             "The circuit level Receive Password"
     ::= { fsIsisExtCircLevelRxPasswordEntry 1 }

     fsIsisExtCircLevelRxPasswordExistState OBJECT-TYPE
         SYNTAX RowStatus
         MAX-ACCESS read-write
         STATUS current
         DESCRIPTION
             "The circuit level receive password exist state"
     ::= { fsIsisExtCircLevelRxPasswordEntry 2 }


-- IPIfAddr Table 

      fsIsisExtIPIfAddrTable    OBJECT-TYPE
         SYNTAX      SEQUENCE OF FsIsisExtIPIfAddrEntry
         MAX-ACCESS        not-accessible
         STATUS            current
         DESCRIPTION
             "IP Interface Address Table used by IS-IS"
         ::= { fsIsisExtIPIf 1 }

      fsIsisExtIPIfAddrEntry    OBJECT-TYPE
         SYNTAX      FsIsisExtIPIfAddrEntry
         MAX-ACCESS        not-accessible
         STATUS            current
         DESCRIPTION
            "  "
         INDEX { fsIsisExtSysInstance, fsIsisExtIPIfIndex,
                 fsIsisExtIPIfSubIndex, fsIsisExtIPIfAddrType, 
                 fsIsisExtIPIfAddr }

         ::= { fsIsisExtIPIfAddrTable 1 }

      FsIsisExtIPIfAddrEntry ::=
         SEQUENCE {
            fsIsisExtIPIfIndex   Integer32,
            fsIsisExtIPIfSubIndex Integer32,
            fsIsisExtIPIfAddrType INTEGER,
            fsIsisExtIPIfAddr   OCTET STRING,
            fsIsisExtIPIfExistState     RowStatus
         }

      fsIsisExtIPIfIndex     OBJECT-TYPE
         SYNTAX Integer32 (1..2000000000)
         MAX-ACCESS        not-accessible
         STATUS            current
         DESCRIPTION
            "The IP Interface Index "
         ::= { fsIsisExtIPIfAddrEntry 1 }

      fsIsisExtIPIfSubIndex     OBJECT-TYPE
         SYNTAX Integer32 (1..2000000000)
         MAX-ACCESS        not-accessible
         STATUS            current
         DESCRIPTION
            "The Sub If Index of the IP If Table"
         ::= { fsIsisExtIPIfAddrEntry 2 }

      fsIsisExtIPIfAddrType     OBJECT-TYPE
         SYNTAX   INTEGER
             {
                 ipv4 (1),
                 ipv6 (2)
             }
         MAX-ACCESS        not-accessible
         STATUS            current
         DESCRIPTION
            "The IPIf Address Type"
         ::= { fsIsisExtIPIfAddrEntry 3 }

      fsIsisExtIPIfAddr     OBJECT-TYPE
         SYNTAX         OCTET STRING (SIZE(4|16))
         MAX-ACCESS        not-accessible
         STATUS            current
         DESCRIPTION
            "The IP Interface Address   "
         ::= { fsIsisExtIPIfAddrEntry 4 }

      fsIsisExtIPIfExistState     OBJECT-TYPE
         SYNTAX         RowStatus
         MAX-ACCESS     read-write
         STATUS         current
         DESCRIPTION
            "IP Interface table Exist state "
         ::= { fsIsisExtIPIfAddrEntry 5 }

-- Log Table

      fsIsisExtLogTable    OBJECT-TYPE
         SYNTAX      SEQUENCE OF FsIsisExtLogEntry
         MAX-ACCESS        not-accessible
         STATUS            current
         DESCRIPTION
            "The System LOG Table used by IS-IS"
         ::= { fsIsisExtLog 1 }

      fsIsisExtLogEntry    OBJECT-TYPE
         SYNTAX      FsIsisExtLogEntry
         MAX-ACCESS        not-accessible
         STATUS            current
         DESCRIPTION
            "The System Log Entry used by IS-IS "
         INDEX { fsIsisExtLogModId }
         ::= { fsIsisExtLogTable 1 }

      FsIsisExtLogEntry ::=
         SEQUENCE {
            fsIsisExtLogModId   INTEGER,
            fsIsisExtLogLevel   Integer32
         }

     fsIsisExtLogModId    OBJECT-TYPE
        SYNTAX  INTEGER {
                adjmodule (0),
                ctlmodule (1),
                updmodule (2),
                decmodule (3),
                tmrmodule (4),
                fltmodule (5),
                rtmmodule (6),
                dllmodule (7),
                bpcmodule (8),
                fwdmodule (9),
                trfmodule (10),
                sbdmodule (11),
                nmgmodule (12),
                dbgmodule (13),
                utlmodule (14),
                intmodule (15),
                crmodule(16)
        }
        MAX-ACCESS  not-accessible
        STATUS            current
        DESCRIPTION
         "The Index of the table which refers to the 
          module"
        ::= { fsIsisExtLogEntry 1}  

      fsIsisExtLogLevel  OBJECT-TYPE
         SYNTAX  Integer32
         MAX-ACCESS  read-write
         STATUS            current
         DESCRIPTION
          " The Log level Flag. Each bit corresponds to
            log level, if set enables log at that level.
            Bit 0 -  Protocol Trace
            Bit 1 - Packet Dump
            Bit 2 - Table Dump
            Bit 3 - Entry Exit Log
            Bits 4-7 - Reserved.
            "
         ::= { fsIsisExtLogEntry 2}   

 -- Adjacency Table     

     fsIsisExtAdjTable OBJECT-TYPE
         SYNTAX SEQUENCE OF FsIsisExtAdjEntry
         MAX-ACCESS not-accessible
         STATUS current
         DESCRIPTION
             "The extended table of adjacencies to Intermediate Systems."
     ::= { fsIsisExtAdj 1 }

     fsIsisExtAdjEntry OBJECT-TYPE
         SYNTAX FsIsisExtAdjEntry
         MAX-ACCESS not-accessible
         STATUS current
         DESCRIPTION
             "Each entry corresponds to one adjacency to an
             Intermediate System on this system."
         INDEX { fsIsisExtSysInstance,
                 fsIsisExtCircIndex,
                 fsIsisExtAdjIndex }
     ::= { fsIsisExtAdjTable 1 }


     FsIsisExtAdjEntry ::=
         SEQUENCE {
             fsIsisExtAdjIndex 
                 Integer32,
             fsIsisExtAdjNeighSysID
                 OCTET STRING,
             fsIsisExtAdjHelperStatus
             	 INTEGER,
             fsIsisExtAdjHelperExitReason
             	 INTEGER,
             fsIsisExtAdjMTID
                 Integer32,
             fsIsisExtAdjHostName
                 OCTET STRING,
             fsIsisExtISAdj3WayState
                 INTEGER,
             fsIsisExtISAdjNbrExtendedCircID
                 Unsigned32
          }

     fsIsisExtAdjIndex OBJECT-TYPE
         SYNTAX Integer32 (1..2000000000)
         MAX-ACCESS not-accessible
         STATUS current
         DESCRIPTION
             "A unique value identifying the IS adjacency from all
             other such adjacencies on this circuit. This value is
             assigned by the system when the adjacency is created
             automatically."
     ::= { fsIsisExtAdjEntry  1 }

   fsIsisExtAdjNeighSysID OBJECT-TYPE
         SYNTAX OCTET STRING (SIZE(0..12))
         MAX-ACCESS read-only
         STATUS current
         DESCRIPTION
             "The system ID and 4 byte circuit ID of the
             neighboring Intermediate System set from
             the source ID field of the Three-Way-Handshake
             information from the neighbor's IIH PDUs."
         REFERENCE "{ISIS.aoi neighbourSystemIds (83)}"
     ::= { fsIsisExtAdjEntry  2 }

    fsIsisExtAdjHelperStatus OBJECT-TYPE
       SYNTAX      INTEGER {
                             notHelping (1),
                             helping (2)
                           }
       MAX-ACCESS  read-only
       STATUS      current
       DESCRIPTION
           " Indicates whether the router is acting as a graceful helper for the restarting  neighbor."
       ::= { fsIsisExtAdjEntry 3 }

    fsIsisExtAdjHelperExitReason OBJECT-TYPE
       SYNTAX      INTEGER { none (1),           -- not attempted
                             inProgress (2),     -- Helping in progress
                             completed (3),      -- successfully completed
                             timedOut (4),       -- timed out
                             topologyChanged (5) -- aborted due to topology
                                                 -- change.
                           }
       MAX-ACCESS  read-only
       STATUS      current
       DESCRIPTION
		       "Describes the outcome of the last attempt at a
           graceful restart "

       ::= { fsIsisExtAdjEntry 4 }
    fsIsisExtAdjMTID    OBJECT-TYPE
        SYNTAX Integer32
        MAX-ACCESS   read-only
        STATUS       current
        DESCRIPTION
           "The supported MT-IDS for the isis Adjacency entry are Bit 0 and Bit 2.
             Bit 0 indicates that supported MT ID is 0 i.e IPV4 (Value is 1) and 
             Bit 2 indicates that supported MT ID is 2 i.e IPV6 (Value is 4)"

       ::= { fsIsisExtAdjEntry 5 }

   fsIsisExtAdjHostName OBJECT-TYPE
         SYNTAX OCTET STRING (SIZE(0..255))
         MAX-ACCESS read-only
         STATUS current
         DESCRIPTION
             "This object specifies the hostname of the neighbour."
     ::= { fsIsisExtAdjEntry  6 }

	fsIsisExtISAdj3WayState OBJECT-TYPE
        SYNTAX INTEGER
            {
                 up (0),
                 initializing (1),
                 down (2),
                 failed (3)
            }
        MAX-ACCESS read-only
        STATUS current
        DESCRIPTION
            "This object specifies the 3Way state of the adjacency.  These are picked
             to match the historical on-the-wire representation
             of the 3Way state and are not intended to match
             isisISAdjState."
        REFERENCE "{ RFC 3373 }"
       ::= { fsIsisExtAdjEntry 7}

	fsIsisExtISAdjNbrExtendedCircID OBJECT-TYPE
        SYNTAX Unsigned32
        MAX-ACCESS read-only
        STATUS current
        DESCRIPTION
            "This object specifies the 4-byte Extended Circuit ID learned from the
             Neighbor during 3-way handshake, or 0."
       ::= { fsIsisExtAdjEntry 8}

--- NOTIFICATION OBJECTS : TRAP SUPPORT -----
    fsIsisTraps  OBJECT IDENTIFIER ::= { fsIsisNotifications 0 }
    fsIsisRestartStatusChange NOTIFICATION-TYPE
        OBJECTS  {
                   fsIsisExtSysActSysID, -- The originator of the trap
                   fsIsisExtRestartStatus,
                   fsIsisExtGRRestartTimeInterval,
                   fsIsisExtRestartExitReason
                 }
        STATUS   current
        DESCRIPTION
            "An fsIsisRestartStatusChange trap signifies that
             there has been a change in the graceful restart
             state for the router. This trap should be
             generated when the router restart status
             changes."
        ::= { fsIsisTraps 1 }

    fsIsisHelperStatusChange NOTIFICATION-TYPE
        OBJECTS {
                  fsIsisExtSysActSysID, -- The originator of the trap
                  fsIsisExtAdjNeighSysID,
                  fsIsisExtAdjHelperStatus,
		  fsIsisExtHelperGraceTimeLimit,
                  fsIsisExtAdjHelperExitReason
                }
        STATUS  current
        DESCRIPTION
            "An fsIsisNbrRestartHelperStatusChange trap signifies that
            there has been a change in the graceful restart
            helper state for the neighbor. This trap should be
            generated when the neighbor restart helper status
            transitions for a neighbor."
        ::= { fsIsisTraps 2 }

 
-- FILTERING OBJECT DEFINITION BEGIN

 fsisisDistInOutRouteMap OBJECT IDENTIFIER ::= { fsIsis 4 }

    fsIsisDistInOutRouteMapTable OBJECT-TYPE
        SYNTAX SEQUENCE OF FsIsisDistInOutRouteMapEntry
        MAX-ACCESS          not-accessible
        STATUS              current
        DESCRIPTION
            "A table describing the configuration of filtering for route map."
    ::= { fsisisDistInOutRouteMap 1 }

    fsIsisDistInOutRouteMapEntry OBJECT-TYPE
        SYNTAX FsIsisDistInOutRouteMapEntry
        MAX-ACCESS          not-accessible
        STATUS              current
        DESCRIPTION
            "Information describing the filtering configuration of single entry."
        INDEX { fsIsisExtSysInstance, fsIsisDistInOutRouteMapName, fsIsisDistInOutRouteMapType }
    ::=  { fsIsisDistInOutRouteMapTable 1 }

    FsIsisDistInOutRouteMapEntry ::= SEQUENCE {
        fsIsisDistInOutRouteMapName         DisplayString,
        fsIsisDistInOutRouteMapType         Integer32,
        fsIsisDistInOutRouteMapValue        Integer32,
        fsIsisDistInOutRouteMapRowStatus    RowStatus
    }

    fsIsisDistInOutRouteMapName OBJECT-TYPE
        SYNTAX              DisplayString (SIZE(1..20))
        MAX-ACCESS          not-accessible
        STATUS              current
        DESCRIPTION
            "Route map name."
    ::=  { fsIsisDistInOutRouteMapEntry 1 }

    fsIsisDistInOutRouteMapType OBJECT-TYPE
        SYNTAX              Integer32(1..3)
        MAX-ACCESS          not-accessible
        STATUS              current
        DESCRIPTION
            "Type of route map to indicate the route map is for
            distribute in or for distribute out or for distance.
            1 - distance
            2 - distribute in
            3 - distribute out"
    ::=  { fsIsisDistInOutRouteMapEntry 2 }

    fsIsisDistInOutRouteMapValue  OBJECT-TYPE
        SYNTAX              Integer32(1..255)
        MAX-ACCESS          read-write
        STATUS              current
        DESCRIPTION
            "Distance value ( this will be unused for distribute list )"
    ::=  { fsIsisDistInOutRouteMapEntry 3 }

    fsIsisDistInOutRouteMapRowStatus OBJECT-TYPE
        SYNTAX              RowStatus
        MAX-ACCESS          read-write
        STATUS              current
        DESCRIPTION
            "The status of this row, by which new entries may be
            created, or old entries deleted from this table."
    ::=  { fsIsisDistInOutRouteMapEntry 4 }

-- FILTERING OBJECT DEFINITION END

-- PREFERENCE OBJECT DEFINITION BEGIN

 fsisisPreferenceGroup OBJECT IDENTIFIER ::= { fsIsis 5 }

    fsIsisPreferenceTable OBJECT-TYPE
        SYNTAX SEQUENCE OF FsIsisPreferenceEntry
        MAX-ACCESS          not-accessible
        STATUS              current
        DESCRIPTION
            "A table describing preference value  for route map."
    ::= { fsisisPreferenceGroup 1 }

    fsIsisPreferenceEntry OBJECT-TYPE
        SYNTAX FsIsisPreferenceEntry
        MAX-ACCESS          not-accessible
        STATUS              current
        DESCRIPTION
            "Information describing preference value of single entry."
        INDEX { fsIsisExtSysInstance }
    ::=  { fsIsisPreferenceTable 1 }

    FsIsisPreferenceEntry ::= SEQUENCE {
        fsIsisPreferenceValue             Integer32,
        fsIsisPreferenceRowStatus         RowStatus
    }

    fsIsisPreferenceValue OBJECT-TYPE
       SYNTAX Integer32 (0..255)
       MAX-ACCESS read-write
       STATUS current
       DESCRIPTION
           "Preference value for IS-IS routes. Use '0' to set default value"
       DEFVAL { 120 }
    ::= { fsIsisPreferenceEntry 2 }

    fsIsisPreferenceRowStatus OBJECT-TYPE
        SYNTAX              RowStatus
        MAX-ACCESS          read-write
        STATUS              current
        DESCRIPTION
            "The status of this row, by which new entries may be
            created, or old entries deleted from this table."
    ::=  { fsIsisPreferenceEntry 3 }

-- PREFERENCE OBJECT DEFINITION END
          
-- Route Redistribution Metric OBJECTs DEFINTION BEGIN 
   fsIsisRRDGroup OBJECT IDENTIFIER ::= { fsIsis 6 } 

    fsIsisRRDMetricTable OBJECT-TYPE
        SYNTAX SEQUENCE OF FsIsisRRDMetricEntry
        MAX-ACCESS          not-accessible
        STATUS              current
        DESCRIPTION
            "This table describes the configuration of metric values to 
             the redistributed routes."
    ::= { fsIsisRRDGroup 1 }

    fsIsisRRDMetricEntry OBJECT-TYPE
        SYNTAX FsIsisRRDMetricEntry
        MAX-ACCESS          not-accessible
        STATUS              current
        DESCRIPTION
            "This object describes the configuration of single entry."
        INDEX {fsIsisExtSysInstance, fsIsisRRDMetricProtocolId}
    ::=  { fsIsisRRDMetricTable 1 }

    FsIsisRRDMetricEntry ::= SEQUENCE {
        fsIsisRRDMetricProtocolId                INTEGER,
        fsIsisRRDMetricValue                    Integer32
    }

    fsIsisRRDMetricProtocolId    OBJECT-TYPE
        SYNTAX              INTEGER
                            {
                              ospf(1),
                              rip(2),
                              connected(3),
                              static(4),
                              bgp(5) 
                             }
        MAX-ACCESS          not-accessible
        STATUS              current
        DESCRIPTION
            "This object specifies the metric Protocol Id."
    ::=  { fsIsisRRDMetricEntry 1 }

    fsIsisRRDMetricValue OBJECT-TYPE
        SYNTAX              Unsigned32 (1..4261412864)
        MAX-ACCESS          read-write
        STATUS              current
        DESCRIPTION
            "The object specifies the metric value to be considered instead of the default value from RTM for the protocol specified. If the value not secified by the 
             user, default metric value is considered."
    ::=  { fsIsisRRDMetricEntry 2 }

-- Router Redistribution OBJECTS DEFINITION END
END
