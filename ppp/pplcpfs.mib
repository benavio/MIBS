-- ###################################################
-- Copyright (C) 2006 Aricent Inc . All Rights Reserved
-- $Id: pplcpfs.mib,v 1.2 2011/04/11 11:08:39 siva Exp $
-- Description: PPP MIB.
-- ####################################################

 
               FSPPPEXT-MIB DEFINITIONS ::= BEGIN 
 
 IMPORTS
     MODULE-IDENTITY, OBJECT-TYPE, 
     enterprises, Integer32   FROM SNMPv2-SMI
     DisplayString           FROM SNMPv2-TC
     ifIndex  FROM IF-MIB;


 futurePPPMIB MODULE-IDENTITY
    LAST-UPDATED "200112061100Z"
    ORGANIZATION "FUTURE SOFTWARE LIMITED"
    CONTACT-INFO 
    "
    FUTURE SOFTWARE LIMITED
    481 Mount Road
    Madras - 600 035
    Phone : +91-44-433 055 0
    E-mail: support@future.futsoft.com"
    DESCRIPTION "Future Software Proprietary MIB"
    ::= { enterprises futuresoftware (2076) 5 } 


          pppExt     OBJECT IDENTIFIER    ::= { futurePPPMIB 1 }
          
          pppExtLink       OBJECT IDENTIFIER ::= { pppExt 1 }

    pppExtLinkConfigTable  OBJECT-TYPE
       SYNTAX          SEQUENCE OF PppExtLinkConfigEntry
       MAX-ACCESS not-accessible
       STATUS     current
       DESCRIPTION
        "Additional Parameters provided for flexibility in configuring
         LCP component of PPP."
      ::=  {  pppExtLink 1  }
     

     pppExtLinkConfigEntry  OBJECT-TYPE
       SYNTAX        PppExtLinkConfigEntry
       MAX-ACCESS not-accessible
       STATUS     current
       DESCRIPTION
        "LCP Parameters for a specific PPP Interface."
       INDEX  { ifIndex  } 
      ::=  {   pppExtLinkConfigTable 1 }


     
    PppExtLinkConfigEntry  ::= 
        SEQUENCE {
        pppExtLinkConfigTxACFC
             INTEGER,
        pppExtLinkConfigRxACFC
             INTEGER,
        pppExtLinkConfigTxPFC
             INTEGER,
        pppExtLinkConfigRxPFC
             INTEGER,
        pppExtLinkConfigLowerIfType
             Integer32,
        pppExtLinkConfigHostName
            DisplayString,
        pppExtKeepAliveTimeOut
            Integer32
      }

     pppExtLinkConfigTxACFC  OBJECT-TYPE
               SYNTAX        INTEGER{
                            disable (1),
                            enable (2)
                        }    
               MAX-ACCESS    read-write
               STATUS        current
               DESCRIPTION
                  "If enabled then local PPP entity can send PPP Data packets
                   with address and control field compressed.(i.e the local
                   entity will configure_ack the ACFC option received in 
                   the configure request)"
               ::= { pppExtLinkConfigEntry 1 }
     
         pppExtLinkConfigRxACFC  OBJECT-TYPE
               SYNTAX        INTEGER{
                            disable (1),
                            enable (2)
                        }    
               MAX-ACCESS    read-write
               STATUS        current
               DESCRIPTION
                  "If enabled implementaion can receive PPP data packets
                  with address and control field compressed.(i.e the local
                  entity will send ACFC option in it's configure request)"
               ::= { pppExtLinkConfigEntry 2 }
     
         pppExtLinkConfigTxPFC  OBJECT-TYPE
               SYNTAX        INTEGER{
                            disable (1),
                            enable (2)
                        }    
               MAX-ACCESS    read-write
               STATUS        current
               DESCRIPTION
                  "If enabled then local PPP entity can send PPP Data packets
                   with protocol field compressed.(i.e the local
                   entity will configure_ack the PFC option received in 
                   the configure request)"
               ::= { pppExtLinkConfigEntry 3 }
     

         pppExtLinkConfigRxPFC  OBJECT-TYPE
               SYNTAX        INTEGER{
                            disable (1),
                            enable (2)
                        }    
               MAX-ACCESS    read-write
               STATUS        current
               DESCRIPTION
                  "If enabled implementaion can receive PPP data packets
                  with protocol field compressed.(i.e the local
                  entity will send PFC option in it's configure request)"
               ::= { pppExtLinkConfigEntry 4 }

    pppExtLinkConfigLowerIfType  OBJECT-TYPE
       SYNTAX        Integer32 
       MAX-ACCESS read-write
       STATUS     deprecated
       DESCRIPTION
              "This identifes the lower layer interface type over
              which the PPP is running.This object is deprecated in 
              favour of 'pppPhysifType'."
       ::=  {   pppExtLinkConfigEntry 5 }

       
    pppExtLinkConfigHostName  OBJECT-TYPE
       SYNTAX        DisplayString
       MAX-ACCESS read-write
       STATUS     current
       DESCRIPTION
                "This is used as the host name field for CHAP 
                Authentication."
       ::=  {   pppExtLinkConfigEntry 6 }
      
    pppExtKeepAliveTimeOut   OBJECT-TYPE
       SYNTAX        Integer32 (0..600)
       MAX-ACCESS    read-write
       STATUS        current
       DESCRIPTION
                "The amount of time in seconds between the transmission of
                 periodic Echo request packets. Echo request packets
                 are transmitted after LCP is up to check whether the
                 peer is alive. The peer is considered inactive if
                 three consecutive requests do not elicit reponses.
                 Setting a value of 0 stops periodic echo request 
                 transmission."
    DEFVAL    { 10 }
     ::= { pppExtLinkConfigEntry 7 }
END
