PW-MPLS-STD-MIB DEFINITIONS ::= BEGIN 
   
  IMPORTS  
     MODULE-IDENTITY, OBJECT-TYPE, Unsigned32, transmission, enterprises 
        FROM SNMPv2-SMI                   -- [RFC2578] 
   
     MODULE-COMPLIANCE, OBJECT-GROUP  
        FROM SNMPv2-CONF                  -- [RFC2580]  
   
     StorageType  
        FROM SNMPv2-TC                    -- [RFC2579] 
   
     InterfaceIndexOrZero  
        FROM IF-MIB                       -- [RFC2863] 
   
     MplsTunnelIndex, MplsTunnelInstanceIndex,  
     MplsLdpIdentifier, MplsLsrIdentifier  
        FROM MPLS-TC-STD-MIB              -- [RFC3810] 
   
     MplsIndexType  
        FROM MPLS-LSR-STD-MIB             -- [RFC3813] 
   
     PwIndexType  
        FROM PW-TC-STD-MIB                 
   
     pwIndex  
        FROM PW-STD-MIB  
   
  ;  
   
  pwMplsStdMIB MODULE-IDENTITY  
     LAST-UPDATED "200602011200Z"  -- 1 February 2006 12:00:00 GMT   
     ORGANIZATION "Pseudo Wire Edge to Edge Emulation (PWE3) Working  
                   Group."  
     CONTACT-INFO  
         "  
          David Zelig, Editor  
          E-mail: davidz@corrigent.com  
   
          Thomas D. Nadeau, Editor  
          Email:  tnadeau@cisco.com  
   
          The PWE3 Working Group (email distribution pwe3@ietf.org,  
          http://www.ietf.org/html.charters/pwe3-charter.html)  
         "  
     DESCRIPTION  
         "This MIB module complements the PW-STD-MIB module for PW   
          operation over MPLS.  
   
         Copyright (C) The Internet Society (2006).  This version  
         of this MIB module is part of RFC yyyy;  see the RFC  
         itself for full legal notices.  
         -- RFC Ed.: replace yyyy with actual RFC number & remove     
         -- this note  
         "        
     -- Revision history.  
      REVISION "200602011200Z"  -- 1 February 2006 12:00:00 GMT   
      DESCRIPTION  
          " First published as RFCWXYZ. "  
  -- RFC Editor: Please replace WXYZ with correct # and remove this -
  -- note 
   
    ::= {enterprises futuresoftware (2076) futureMpls (13) 6}  
   
  -- RFC Editor: To be assigned by IANA. Please replace XXX 
  -- with the assigned value and remove this note. 
   
  -- Top-level components of this MIB.  
   
   -- Notifications  
   pwMplsNotifications OBJECT IDENTIFIER   
                                 ::= { pwMplsStdMIB 0 }  
   
  -- Tables, Scalars  
  pwMplsObjects       OBJECT IDENTIFIER  
                                ::= { pwMplsStdMIB 1 }  
  -- Conformance  
  pwMplsConformance   OBJECT IDENTIFIER   
                                ::= { pwMplsStdMIB 2 }  
   
  -- PW MPLS table  
   
  pwMplsTable   OBJECT-TYPE  
     SYNTAX        SEQUENCE OF PwMplsEntry  
     MAX-ACCESS    not-accessible  
     STATUS        current  
     DESCRIPTION  
         "This table controls MPLS specific parameters when the PW is  
          going to be carried over MPLS PSN."  
     ::= { pwMplsObjects 1 }  
   
  pwMplsEntry   OBJECT-TYPE  
     SYNTAX        PwMplsEntry  
     MAX-ACCESS    not-accessible  
     STATUS        current  
     DESCRIPTION  
          "A row in this table represents parameters specific to MPLS   
           PSN for a pseudo wire (PW). The row is created   
           automatically by the local agent if the pwPsnType is   
           MPLS. It is indexed by pwIndex, which uniquely   
           identifying a singular PW.  
          "  
     INDEX  { pwIndex }  
   
        ::= { pwMplsTable 1 }  
   
  PwMplsEntry ::= SEQUENCE {  
        pwMplsMplsType          BITS,  
        pwMplsExpBitsMode       INTEGER,  
        pwMplsExpBits           Unsigned32,  
        pwMplsTtl               Unsigned32,  
        pwMplsLocalLdpID        MplsLdpIdentifier,  
        pwMplsLocalLdpEntityID  MplsLsrIdentifier,  
        pwMplsPeerLdpID         MplsLdpIdentifier,  
        pwMplsStorageType       StorageType  
     }  
   
  pwMplsMplsType OBJECT-TYPE   
     SYNTAX   BITS {  
         mplsTe    (0),  
         mplsNonTe (1),  
         pwOnly    (2)  
              }  
     MAX-ACCESS    read-write  
     STATUS        current  
     DESCRIPTION  
          "Set by the operator to indicate the outer tunnel types, if  
           exists. mplsTe(0) is used if the outer tunnel was set-up   
           by MPLS-TE, and mplsNonTe(1) is used the outer tunnel was   
           set up by LDP or manually. Combination of mplsTe(0) and   
           mplsNonTe(1) may exist together.  
           pwOnly(2) is used if there is no outer tunnel label, i.e.  
           in static provisioning without MPLS tunnel. pwOnly(2)  
           cannot be combined with mplsNonTe(1) or mplsTe(0)."  
     DEFVAL { { mplsNonTe } }  
     ::= { pwMplsEntry 1 }  
   
  pwMplsExpBitsMode OBJECT-TYPE   
     SYNTAX   INTEGER {  
         outerTunnel      (1),  
         specifiedValue   (2),  
         serviceDependant (3)  
              }  
   
     MAX-ACCESS    read-write  
     STATUS        current  
     DESCRIPTION  
         "Set by the operator to indicate the way the PW shim label  
          EXP bits are to be determined. The value of outerTunnel(1)  
          is used where there is an outer tunnel - pwMplsMplsType   
          is mplsTe(0) or mplsNonTe(1). Note that in this case there   
          is no need to mark the PW label with the EXP bits since the  
          PW label is not visible to the intermediate nodes.  
          If there is no outer tunnel, specifiedValue(2) indicates   
          that the value is specified by pwMplsExpBits, and   
          serviceDependant(3) indicates that the EXP bits are set   
          based on a rule which is implementation specific."  
   
     DEFVAL { outerTunnel }  
     ::= { pwMplsEntry 2 }  
   
  pwMplsExpBits OBJECT-TYPE   
     SYNTAX        Unsigned32 (0..7)  
     MAX-ACCESS    read-write  
     STATUS        current  
     DESCRIPTION  
          "Set by the operator to indicate the MPLS EXP bits to be   
           used on the PW shim label if pwMplsExpBitsMode is    
           specifiedValue(2), zero otherwise."  
     DEFVAL { 0 }  
     ::= { pwMplsEntry 3 }  
   
  pwMplsTtl OBJECT-TYPE   
     SYNTAX        Unsigned32 (0..255)  
     MAX-ACCESS    read-write  
     STATUS        current  
     DESCRIPTION  
          "Set by the operator to indicate the PW TTL value to be   
           used on the PW shim label."  
     DEFVAL { 2 }  
     ::= { pwMplsEntry 4 }  
   
  pwMplsLocalLdpID OBJECT-TYPE   
     SYNTAX        MplsLdpIdentifier  
     MAX-ACCESS    read-write  
     STATUS        current  
     DESCRIPTION  
          "The local LDP identifier of the LDP entity creating  
           this PW in the local node. As the PW labels are always  
           set from the per platform label space, the last two octets   
           in the LDP ID MUST be always both zeros."  
     REFERENCE  
          "'LDP specifications', RFC 3036 section 2.2.2."  
     ::= { pwMplsEntry 5 }  
   
  pwMplsLocalLdpEntityID OBJECT-TYPE   
     SYNTAX        MplsLsrIdentifier  
     MAX-ACCESS    read-write  
     STATUS        current  
     DESCRIPTION  
          "The local node LDP Entity ID of the LDP entity creating  
           this PW. Should return the value of all zeros if not   
           used."  
     ::= { pwMplsEntry 6 }  
   
   
  pwMplsPeerLdpID OBJECT-TYPE   
     SYNTAX        MplsLdpIdentifier  
     MAX-ACCESS    read-only  
     STATUS        current  
     DESCRIPTION  
          "The peer LDP identifier as identified from the LDP   
           session. Should return the value of zero if not applicable  
           or not known yet."  
     ::= { pwMplsEntry 7 }  
   
  pwMplsStorageType OBJECT-TYPE   
     SYNTAX        StorageType  
     MAX-ACCESS    read-write  
     STATUS        current  
     DESCRIPTION  
         "This variable indicates the storage type for this row."  
     ::= { pwMplsEntry 8 }  
   
  -- End of PW MPLS table  
   
  -- Pseudo Wire MPLS Outbound Tunnel table  
   
  pwMplsOutboundTable   OBJECT-TYPE  
     SYNTAX        SEQUENCE OF PwMplsOutboundEntry  
     MAX-ACCESS    not-accessible  
     STATUS        current  
     DESCRIPTION  
         "This table reports and configure the current outbound MPLS   
          tunnels (i.e. toward the PSN) or the physical interface in   
          case of PW label only that carry the PW traffic. It also   
          reports the current outer tunnel and LSP which forward the   
          PW traffic."  
     ::= { pwMplsObjects 2 }  
   
  pwMplsOutboundEntry OBJECT-TYPE  
     SYNTAX        PwMplsOutboundEntry  
     MAX-ACCESS    not-accessible  
     STATUS        current  
     DESCRIPTION  
         "A row in this table configures the outer tunnel used for   
          carrying the PW traffic toward the PSN.  
          In the case of PW label only, it configures the interface   
          that will carry the PW traffic.  
   
          An entry in this table augments the pwMplsEntry, and is  
          created automatically when the corresponding row has been  
          created by the agent in the pwMplsEntry.  
   
          This table points to the appropriate MPLS MIB module.   
          In the MPLS-TE case, the 3 variables relevant to the   
          indexing of a TE tunnel head-end are used as in   
          MPLS-TE-STD-MIB are to be configured, and the tunnel   
          instance indicates the LSP that is currently in use for   
          forwarding the traffic.  
   
          In case of signaled Non-TE MPLS (an outer tunnel label   
          assigned by LDP) the table points to the XC entry in the   
          LSR-STD-MIB. If the Non-TE MPLS tunnel is manually   
          configured, the operator configures the XC pointer to this  
          tunnel.  
   
          In case of PW label only (no outer tunnel) the ifIndex of   
          the port to carry the PW is configured here.   
   
          It is possible to associate a PW to one TE tunnel head-end   
          and a non-TE tunnel together. An indication in this table   
          will report the currently active one, In addition, in the   
          TE case the table reports the active tunnel instance   
          (i.e. the specific LSP in use).  
         "      
   
     AUGMENTS { pwMplsEntry }  
   
        ::= { pwMplsOutboundTable 1 }  
   
  PwMplsOutboundEntry ::= SEQUENCE {  
        pwMplsOutboundLsrXcIndex           MplsIndexType,  
        pwMplsOutboundTunnelIndex          MplsTunnelIndex,  
        pwMplsOutboundTunnelInstance       MplsTunnelInstanceIndex,  
        pwMplsOutboundTunnelLclLSR         MplsLsrIdentifier,  
        pwMplsOutboundTunnelPeerLSR        MplsLsrIdentifier,  
        pwMplsOutboundIfIndex              InterfaceIndexOrZero,  
        pwMplsOutboundTunnelTypeInUse      INTEGER  
        }  
   
  pwMplsOutboundLsrXcIndex      OBJECT-TYPE  
     SYNTAX        MplsIndexType  
     MAX-ACCESS    read-write  
     STATUS        current  
     DESCRIPTION  
         "This object is applicable if pwMplsMplsType mplsNonTe(1)  
          bit is set, and MUST return a value of zero otherwise.  
          If the outer tunnel is signaled, the object is read-only   
          and indicates the XC index in the MPLS-LSR-STD-MIB of the  
          outer tunnel toward the peer. Otherwise (tunnel is set-up   
          manually) the operator defines the XC index of the manually   
          created outer tunnel through this object.  
         "  
     ::= { pwMplsOutboundEntry 1 }  
   
   
  pwMplsOutboundTunnelIndex         OBJECT-TYPE  
     SYNTAX        MplsTunnelIndex  
     MAX-ACCESS    read-write  
     STATUS        current  
     DESCRIPTION  
         "This object is applicable if pwMplsMplsType mplsTe(0)  
          bit is set, and MUST return a value of zero otherwise.  
          It is Part of set of indexes for outbound tunnel.  
          The operator set this object to represent the desired  
          tunnel head-end toward the peer for carrying the PW   
          traffic.  
         "  
     ::= { pwMplsOutboundEntry  2 }   
   
  pwMplsOutboundTunnelInstance      OBJECT-TYPE  
     SYNTAX        MplsTunnelInstanceIndex  
     MAX-ACCESS    read-only  
     STATUS        current  
     DESCRIPTION  
         "This object is applicable if pwMplsMplsType mplsTe(0)   
          bit is set, and MUST return a value of zero otherwise.  
          It indicates the actual tunnel instance that is currently   
          active and carrying the PW traffic - it should return the   
          value of zero until if the information from the MPLS-TE   
          application is not yet known.  
         "  
     ::= { pwMplsOutboundEntry   3 }   
   
  pwMplsOutboundTunnelLclLSR        OBJECT-TYPE  
     SYNTAX        MplsLsrIdentifier  
     MAX-ACCESS    read-write  
     STATUS        current  
     DESCRIPTION   
         "This object is applicable if pwMplsMplsType mplsTe(0)   
          bit is set, and MUST return a value of all zeros otherwise.  
          It is part of set of indexes for outbound tunnel.  
          The operator set this object to represent the desired  
          tunnel head-end toward the peer for carrying the PW   
          traffic.  
         "  
     ::= { pwMplsOutboundEntry   4 }   
   
  pwMplsOutboundTunnelPeerLSR       OBJECT-TYPE  
     SYNTAX        MplsLsrIdentifier  
     MAX-ACCESS    read-write  
     STATUS        current  
     DESCRIPTION  
         "This object is applicable if pwMplsMplsType mplsTe(0)  
          bit is set, and MUST return a value of zero otherwise.  
          It is part of set of indexes for outbound tunnel. It is  
          typically equal to pwPeerAddr.  
         "  
     ::= { pwMplsOutboundEntry   5 }   
   
  pwMplsOutboundIfIndex       OBJECT-TYPE  
     SYNTAX         InterfaceIndexOrZero  
     MAX-ACCESS     read-write  
     STATUS         current  
     DESCRIPTION  
         "This object is applicable if pwMplsMplsType pwOnly(0)  
          bit is set, and MUST return a value of zero otherwise.  
          The operator configure the ifIndex of the outbound port  
          in this case.  
         "  
     ::= { pwMplsOutboundEntry   6 }  
   
  pwMplsOutboundTunnelTypeInUse OBJECT-TYPE  
     SYNTAX         INTEGER {  
                    notYetKnown (1),  
                    mplsTe      (2),  
                    mplsNonTe   (3),  
                    pwOnly      (4)  
     }  
     MAX-ACCESS     read-only  
     STATUS         current  
     DESCRIPTION  
         "This object indicates the current tunnel that is carrying  
          the PW traffic.  
          The value of notYetKnown(1) should be used if the agent is   
          currently unable to determine which tunnel or interface is   
          carrying the PW, for example because both tunnels are in   
          operational status down.  
         "  
     ::= { pwMplsOutboundEntry   7 }  
   
  -- End of PW MPLS Outbound Tunnel table  
   
  -- PW MPLS inbound table  
   
  pwMplsInboundTable OBJECT-TYPE   
     SYNTAX           SEQUENCE OF PwMplsInboundEntry  
     MAX-ACCESS       not-accessible  
     STATUS           current  
     DESCRIPTION  
         "This table indicates the PW LDP XC entry in the   
          MPLS-LSR-STD-MIB for signaled PWs.  
         "  
     ::= { pwMplsObjects 3 }  
   
   
  pwMplsInboundEntry OBJECT-TYPE  
     SYNTAX           PwMplsInboundEntry  
     MAX-ACCESS       not-accessible  
     STATUS           current  
     DESCRIPTION  
          "A row in this table is created by the agent   
           for each signaled PW, and shows the XC index related to   
           the PW signaling in the inbound direction in the   
           MPLS-LSR-STD-MIB that controls and display the information  
           for all the LDP signaling processes in the local node.  
          "  
     INDEX  { pwIndex }  
   
        ::= { pwMplsInboundTable 1 }  
   
  PwMplsInboundEntry ::= SEQUENCE {  
        pwMplsInboundXcIndex           MplsIndexType  
     }  
   
  pwMplsInboundXcIndex OBJECT-TYPE  
     SYNTAX        MplsIndexType  
     MAX-ACCESS    read-only  
     STATUS        current  
     DESCRIPTION  
         "The XC index representing this PW in the inbound   
          direction. Should return the value of zero if the   
          information is not yet known."  
     ::= { pwMplsInboundEntry 1 }  
   
  -- End of PW MPLS inbound table  
   
  -- PW to Non-TE mapping Table.  
   
  pwMplsNonTeMappingTable OBJECT-TYPE   
     SYNTAX           SEQUENCE OF PwMplsNonTeMappingEntry  
     MAX-ACCESS       not-accessible  
     STATUS           current  
     DESCRIPTION  
         "This table indicates outbound Tunnel to a PW in non-TE   
          applications, maps the PW to it's (inbound) XC entry, and   
          indicates the PW to physical interface mapping for a PW   
          label to physical interface a PW label is in use without   
          outer tunnel.  
         "  
     ::= { pwMplsObjects 4 }  
   
  pwMplsNonTeMappingEntry OBJECT-TYPE  
     SYNTAX           PwMplsNonTeMappingEntry  
     MAX-ACCESS       not-accessible  
     STATUS           current  
     DESCRIPTION  
          "A row in this table displays the association  
           between the PW and  
           - it's non-TE MPLS outbound outer Tunnel or,  
           - it's XC entry in the MPLS-LSR-STD-MIB,   
           - it's physical interface if there is no outer tunnel   
             (PW label only) and manual configuration.  
   
           Rows are created in this table by the by the   
           agent depending on the setting of pwMplsMplsType:  
   
           - If pwMplsMplsType mplsNonTe(1) bit is set, the agent   
           creates a row for the outbound direction   
           (pwMplsNonTeMappingDirection set to psnBound(1)).   
           The pwMplsNonTeMappingXcIndex holds the XC index in the   
           MPLS-LSR-STD-MIB of the PSN bound outer tunnel.   
           pwMplsNonTeMappingIfIndex MUST be zero for this row.  
   
           - If pwMplsMplsType pwOnly(2) bit is set, the agent   
           creates a row for the outbound direction   
           (pwMplsNonTeMappingDirection set to psnBound(1)).   
           The pwMplsNonTeMappingIfIndex holds the ifIndex of the   
           physical port this PW will use in the outbound direction.  
           pwMplsNonTeMappingXcIndex MUST be zero for this row.  
   
           - If the PW has been set-up by signaling protocol (i.e.   
           pwOwner equal pwIdFecSignaling(2) or   
           genFecSignaling(3)), the agent creates a row for the   
           inbound direction (pwMplsNonTeMappingDirection set to   
           fromPsn(2)).  
           The pwMplsNonTeMappingXcIndex holds the XC index in the   
           MPLS-LSR-STD-MIB of the PW LDP generated XC entry.   
           pwMplsNonTeMappingIfIndex MUST be zero for this row.  
   
           An application can use this table to quickly retrieve the   
           PW carried over specific non-TE MPLS outer tunnel or   
           physical interface.  
           "  
   
     INDEX  { pwMplsNonTeMappingDirection,  
              pwMplsNonTeMappingXcIndex,  
              pwMplsNonTeMappingIfIndex,  
              pwMplsNonTeMappingVcIndex }  
   
        ::= { pwMplsNonTeMappingTable 1 }  
   
  PwMplsNonTeMappingEntry ::= SEQUENCE {  
        pwMplsNonTeMappingDirection         INTEGER,  
        pwMplsNonTeMappingXcIndex           MplsIndexType,  
        pwMplsNonTeMappingIfIndex           InterfaceIndexOrZero,  
        pwMplsNonTeMappingVcIndex           PwIndexType  
     }  
   
  pwMplsNonTeMappingDirection OBJECT-TYPE  
     SYNTAX        INTEGER {  
                   psnBound (1),   
                   fromPsn  (2)   
     }  
     MAX-ACCESS    not-accessible  
     STATUS        current  
     DESCRIPTION  
         "Index for the conceptual XC row identifying Tunnel to PW   
          mappings, indicating the direction of packet flow the entry  
          is related too.  
          psnBound(1) indicates that the entry is related to  
          packets toward the PSN.    
          fromPsn(2) indicates that the entry is related to   
          packets coming from the PSN.  
         "  
     ::= { pwMplsNonTeMappingEntry 1 }  
   
  pwMplsNonTeMappingXcIndex OBJECT-TYPE  
     SYNTAX        MplsIndexType  
     MAX-ACCESS    not-accessible  
     STATUS        current  
     DESCRIPTION  
         "See the description clause of pwMplsNonTeMappingEntry for  
          the usage guidelines of this object."  
     ::= { pwMplsNonTeMappingEntry 2 }  
   
  pwMplsNonTeMappingIfIndex  OBJECT-TYPE  
     SYNTAX        InterfaceIndexOrZero  
     MAX-ACCESS    not-accessible  
     STATUS        current  
     DESCRIPTION  
         "See the description clause of pwMplsNonTeMappingEntry for  
          the usage guidelines of this object."  
     ::= { pwMplsNonTeMappingEntry 3 }  
   
  pwMplsNonTeMappingVcIndex  OBJECT-TYPE  
     SYNTAX        PwIndexType  
     MAX-ACCESS    read-only  
     STATUS        current  
     DESCRIPTION  
         "The value that represent the PW in the pwTable."  
     ::= { pwMplsNonTeMappingEntry 4 }  
   
  -- End of PW to Non-TE mapping Table.  
   
   
  -- PW to TE MPLS tunnels mapping Table.  
   
  pwMplsTeMappingTable OBJECT-TYPE   
     SYNTAX           SEQUENCE OF PwMplsTeMappingEntry  
     MAX-ACCESS       not-accessible  
     STATUS           current  
     DESCRIPTION  
         "This table enable the retrieval of a PW association to the   
          outbound MPLS tunnel for MPLS-TE applications."  
     ::= { pwMplsObjects 5 }  
   
  pwMplsTeMappingEntry OBJECT-TYPE  
     SYNTAX           PwMplsTeMappingEntry  
     MAX-ACCESS       not-accessible  
     STATUS           current  
     DESCRIPTION  
          "A row in this table represents the association  
           between a PW and it's MPLS-TE outer (head-end) Tunnel.  
   
           An application can use this table to quickly retrieve the   
           list of the PWs that are configured on a specific MPLS TE   
           outer tunnel.  
   
           The pwMplsTeMappingTunnelInstance reports the actual  
           LSP out of the tunnel head-end that is currently   
           forwarding the traffic.  
   
           The table in indexed by the head-end indexes of a TE   
           tunnel and the PW index.  
          "  
   
     INDEX  { pwMplsTeMappingTunnelIndex,   
              pwMplsTeMappingTunnelInstance,  
              pwMplsTeMappingTunnelPeerLsrID,  
              pwMplsTeMappingTunnelLocalLsrID,  
              pwMplsTeMappingVcIndex }  
   
        ::= { pwMplsTeMappingTable 1 }  
   
  PwMplsTeMappingEntry ::= SEQUENCE {  
        pwMplsTeMappingTunnelIndex       MplsTunnelIndex,  
        pwMplsTeMappingTunnelInstance    MplsTunnelInstanceIndex,  
        pwMplsTeMappingTunnelPeerLsrID   MplsLsrIdentifier,  
        pwMplsTeMappingTunnelLocalLsrID  MplsLsrIdentifier,  
        pwMplsTeMappingVcIndex           PwIndexType  
     }  
   
  pwMplsTeMappingTunnelIndex OBJECT-TYPE  
     SYNTAX        MplsTunnelIndex  
     MAX-ACCESS    not-accessible  
     STATUS        current  
     DESCRIPTION  
         "Primary index for the conceptual row identifying the   
          MPLS-TE tunnel that is carrying the PW traffic."  
     ::= { pwMplsTeMappingEntry 1 }  
   
  pwMplsTeMappingTunnelInstance OBJECT-TYPE  
     SYNTAX        MplsTunnelInstanceIndex  
     MAX-ACCESS    not-accessible  
     STATUS        current  
     DESCRIPTION  
         "This object identify the MPLS-TE LSP that is carrying the   
          PW traffic. Should return the value of zero if the   
          information of the specific LSP is not yet known.  
          Note that based on the recommendation in the   
          MPLS-TC-STD-MIB, instance index 0 should refer to the   
          configured tunnel interface."  
     ::= { pwMplsTeMappingEntry 2 }  
   
  pwMplsTeMappingTunnelPeerLsrID  OBJECT-TYPE  
     SYNTAX        MplsLsrIdentifier  
     MAX-ACCESS    not-accessible  
     STATUS        current  
     DESCRIPTION  
         "Identifies the Peer LSR when the outer tunnel is MPLS-TE   
          based."  
     ::= { pwMplsTeMappingEntry 3 }  
   
  pwMplsTeMappingTunnelLocalLsrID  OBJECT-TYPE  
     SYNTAX        MplsLsrIdentifier  
     MAX-ACCESS    not-accessible  
     STATUS        current  
     DESCRIPTION  
         "Identifies the local LSR."  
     ::= { pwMplsTeMappingEntry 4 }  
   
  pwMplsTeMappingVcIndex  OBJECT-TYPE  
     SYNTAX        PwIndexType  
     MAX-ACCESS    read-only  
     STATUS        current  
     DESCRIPTION  
         "The value that represent the PW in the pwTable."  
     ::= { pwMplsTeMappingEntry 5 }  
   
  -- End of PW to TE MPLS tunnels mapping Table.  
   
  -- conformance information  
   
  pwMplsGroups      OBJECT IDENTIFIER ::= { pwMplsConformance 1 }  
  pwMplsCompliances OBJECT IDENTIFIER ::= { pwMplsConformance 2 }  
   
  -- Compliance requirement for fully compliant implementations.  
   
  pwMplsModuleFullCompliance MODULE-COMPLIANCE  
      STATUS  current  
      DESCRIPTION  
              "The compliance statement for agents that provide full  
               support for PW-MPLS MIB Module. Such devices can  
               then be monitored and also be configured using  
               this MIB module."  
   
     MODULE  -- this module  
     MANDATORY-GROUPS { pwMplsGroup,  
                        pwMplsOutboundMainGroup,  
                        pwMplsInboundGroup,  
                        pwMplsMappingGroup  
                       }  
   
     GROUP        pwMplsOutboundTeGroup  
     DESCRIPTION "This group MUST be supported if the implementation  
                  allows MPLS TE tunnels to carry PW traffic.   
                  "  
   
     OBJECT       pwMplsMplsType  
     DESCRIPTION "Support of pwOnly(2) is not required. At least one  
                  of mplsTe(0) or mplsNonTe(1) MUST be supported if   
                  signaling of PW is supported.  
                  "  
   
     OBJECT       pwMplsExpBitsMode  
     DESCRIPTION "Support of specifiedValue(2) and  
                  serviceDependant(3) is optional.  
                  "  
   
     OBJECT       pwMplsLocalLdpID  
     MIN-ACCESS   read-only  
     DESCRIPTION "A read-write access is required if the   
                  implementation supports more than one LDP entity   
                  identifier for PW signaling.  
                  "  
   
     OBJECT       pwMplsLocalLdpEntityID  
     MIN-ACCESS   read-only  
     DESCRIPTION "A read-write access is required if the   
                  implementation supports more than one LDP entity   
                  index for PW signaling.  
                  "  
   
     OBJECT       pwMplsOutboundLsrXcIndex  
     MIN-ACCESS   read-only  
     DESCRIPTION "A value other than zero MUST be supported if the  
                  implementation support non TE signaling of the   
                  outer tunnel.  
                  A read-write access MUST be supported if the  
                  implementation supports manually setting of the PW  
                  labels and carrying them over non-TE tunnels.  
                  "  
   
     OBJECT       pwMplsOutboundIfIndex  
     MIN-ACCESS   read-only  
     DESCRIPTION "A value other than zero and read-write operations  
                  MUST be supported if the implementation supports   
                  manully configured PW without MPLS outer tunnel.  
                  "  
      ::= { pwMplsCompliances 1 }  
   
  -- Compliance requirement for Read Only compliant implementations.  
   
  pwMplsModuleReadOnlyCompliance MODULE-COMPLIANCE  
      STATUS  current  
      DESCRIPTION  
              "The compliance statement for agents that provide read  
               only support for PW-MPLS MIB Module. Such devices can  
               then be monitored but cannot be configured using this  
               MIB module."  
   
     MODULE  -- this module  
     MANDATORY-GROUPS { pwMplsGroup,  
                        pwMplsOutboundMainGroup,  
                        pwMplsInboundGroup,  
                        pwMplsMappingGroup  
                       }  
   
     GROUP        pwMplsOutboundTeGroup  
     DESCRIPTION "This group MUST be supported if the implementation  
                  allows MPLS TE tunnels to carry PW traffic.   
                  "  
   
     OBJECT       pwMplsMplsType  
     MIN-ACCESS   read-only  
     DESCRIPTION "Write access is not required.  
                  Support of pwOnly(2) is not required. At least one  
                  of mplsTe(0) or mplsNonTe(1) MUST be supported if   
                  signaling of PW is supported.  
                  "  
   
     OBJECT       pwMplsExpBitsMode  
     MIN-ACCESS   read-only  
     DESCRIPTION "Write access is not required.  
                  Support of specifiedValue(2) and 
  serviceDependant(3)  
                  is optional.  
                  "  
   
     OBJECT       pwMplsExpBits  
     MIN-ACCESS   read-only  
     DESCRIPTION "Write access is not required.  
                  "  
     OBJECT       pwMplsTtl  
     MIN-ACCESS   read-only  
     DESCRIPTION "Write access is not required.  
                  "  
   
     OBJECT       pwMplsLocalLdpID  
     MIN-ACCESS   read-only  
     DESCRIPTION "Write access is not required.  
                  "  
   
     OBJECT       pwMplsLocalLdpEntityID  
     MIN-ACCESS   read-only  
     DESCRIPTION "Write access is not required.  
                  "  
   
     OBJECT       pwMplsStorageType  
     MIN-ACCESS   read-only  
     DESCRIPTION "Write access is not required.  
                  "  
   
     OBJECT       pwMplsOutboundLsrXcIndex  
     MIN-ACCESS   read-only  
     DESCRIPTION "Write access is not required.  
                  A value other than zero MUST be supported if the  
                  implementation support non TE signaling of the   
                  outer tunnel.  
                  "  
   
     OBJECT       pwMplsOutboundTunnelIndex  
     MIN-ACCESS   read-only  
     DESCRIPTION "Write access is not required.  
                  "  
   
     OBJECT       pwMplsOutboundTunnelLclLSR  
     MIN-ACCESS   read-only  
     DESCRIPTION "Write access is not required.  
                  "  
   
     OBJECT       pwMplsOutboundTunnelPeerLSR  
     MIN-ACCESS   read-only  
     DESCRIPTION "Write access is not required.  
                  "  
   
     OBJECT       pwMplsOutboundIfIndex  
     MIN-ACCESS   read-only  
     DESCRIPTION "Write access is not required.  
                  A value other than zero MUST be supported if the   
                  implementation supports manually configured PW   
                  without MPLS outer tunnel.  
                  "  
      ::= { pwMplsCompliances 2 }  
   
  -- Units of conformance.  
   
  pwMplsGroup OBJECT-GROUP   
     OBJECTS {  
              pwMplsMplsType,  
              pwMplsExpBitsMode,  
              pwMplsExpBits,  
              pwMplsTtl,  
              pwMplsLocalLdpID,  
              pwMplsLocalLdpEntityID,  
              pwMplsPeerLdpID,  
              pwMplsStorageType  
            }  
   
     STATUS  current  
     DESCRIPTION  
         "Collection of objects needed for PW over MPLS PSN   
          configuration."  
     ::= { pwMplsGroups 1 }  
   
  pwMplsOutboundMainGroup OBJECT-GROUP   
     OBJECTS {  
              pwMplsOutboundLsrXcIndex,  
              pwMplsOutboundIfIndex,  
              pwMplsOutboundTunnelTypeInUse  
            }  
   
     STATUS  current  
     DESCRIPTION  
         "Collection of objects needed for outbound association of   
          PW and MPLS tunnel."  
     ::= { pwMplsGroups 2 }  
   
  pwMplsOutboundTeGroup OBJECT-GROUP   
     OBJECTS {  
              pwMplsOutboundTunnelIndex,  
              pwMplsOutboundTunnelInstance,  
              pwMplsOutboundTunnelLclLSR,  
              pwMplsOutboundTunnelPeerLSR  
            }  
   
     STATUS  current  
     DESCRIPTION  
         "Collection of objects needed for outbound association of   
          PW and MPLS TE tunnel."  
     ::= { pwMplsGroups 3 }  
   
  pwMplsInboundGroup OBJECT-GROUP   
     OBJECTS {   
              pwMplsInboundXcIndex  
            }  
   
     STATUS  current  
     DESCRIPTION  
         "Collection of objects needed for inbound PW presentation.  
          This group MUST be supported if PW signaling through LDP is   
          used."  
     ::= { pwMplsGroups 4 }  
   
  pwMplsMappingGroup OBJECT-GROUP   
     OBJECTS {  
              pwMplsNonTeMappingVcIndex,  
              pwMplsTeMappingVcIndex  
            }  
   
     STATUS  current  
     DESCRIPTION  
         "Collection of objects needed for mapping association of   
          PW and MPLS tunnel."  
     ::= { pwMplsGroups 5 }  
   
  END
