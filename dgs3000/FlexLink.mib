-- ***************************************************************** 
--  FlexLink.mib : FLEXLINK MIB
-- 
--  Copyright (c) 2015 D-Link Corporation, all rights reserved.
--   
-- ***************************************************************** 
FLEX-LINK-MIB DEFINITIONS ::= BEGIN


	IMPORTS
            MODULE-IDENTITY,
            OBJECT-TYPE,
            NOTIFICATION-TYPE,
            Unsigned32
                FROM SNMPv2-SMI
 	    RowStatus,TruthValue,MacAddress   
                FROM SNMPv2-TC
            MODULE-COMPLIANCE, OBJECT-GROUP
                FROM SNMPv2-CONF
	    ifIndex, InterfaceIndex, InterfaceIndexOrZero
            	FROM IF-MIB
            dlink-common-mgmt                     
                FROM DLINK-ID-REC-MIB;  



	swFlexLinkMIB MODULE-IDENTITY
            LAST-UPDATED "201509020000Z"
            ORGANIZATION "D-Link Corp."
            CONTACT-INFO
                "        D-Link Corporation

                 Postal: No. 289, Sinhu 3rd Rd., Neihu District,
                         Taipei City 114, Taiwan, R.O.C
                 Tel:     +886-2-66000123
                 E-mail: tsd@dlink.com.tw
                "
            DESCRIPTION
                "This MIB module defines objects for extending the configuration of 
                FLEXLINKS. "
            
            REVISION "201509020000Z"
            DESCRIPTION
                "This is the first version of the MIB file."

            ::= { dlink-common-mgmt 114 }


-- ----------------------------------------------------------------------------- 
   	swFlexLinkMgmt         OBJECT IDENTIFIER ::= { swFlexLinkMIB 1 }
-- -----------------------------------------------------------------------------
	swFlexLinkTable OBJECT-TYPE
		SYNTAX      SEQUENCE OF SwFlexLinkEntry
	  	MAX-ACCESS  not-accessible
	  	STATUS      current
	  	DESCRIPTION
	    	"A table that contains Flex Link group information."
		::= { swFlexLinkMgmt 1 }

	swFlexLinkEntry OBJECT-TYPE
		SYNTAX      SwFlexLinkEntry
	  	MAX-ACCESS  not-accessible
	  	STATUS      current
		DESCRIPTION
			"A list of Flex Link group information."
		INDEX    {swFlexLinkGroupID}
		::= { swFlexLinkTable 1 }

	SwFlexLinkEntry ::= SEQUENCE {
		swFlexLinkGroupID    	INTEGER,
	  	swFlexLinkPrimaryPort	INTEGER,
	  	swFlexLinkBackupPort	INTEGER,
		swFlexLinkPrimaryStatus	INTEGER,
	  	swFlexLinkBackupStatus	INTEGER,
		swFlexLinkRowStatus    	RowStatus
		}
	swFlexLinkGroupID OBJECT-TYPE
        SYNTAX  INTEGER(1..65535)
        MAX-ACCESS  not-accessible
        STATUS  current
        DESCRIPTION
            "This object indicates the Flex Link group ID."
        ::= { swFlexLinkEntry 1 }

	swFlexLinkPrimaryPort OBJECT-TYPE
	    SYNTAX      INTEGER
	    MAX-ACCESS  read-create
	    STATUS      current
	    DESCRIPTION
	        "This object indicates the primary port of Flex Link pair ."
	    ::= { swFlexLinkEntry 2 }

	swFlexLinkBackupPort OBJECT-TYPE
	    SYNTAX      INTEGER
	    MAX-ACCESS  read-create
	    STATUS      current
	    DESCRIPTION
    		"This object indicates the backup port of Flex Link pair ."
	    ::= { swFlexLinkEntry 3 }
	
	swFlexLinkPrimaryStatus OBJECT-TYPE
	    SYNTAX      INTEGER{
			inActive(0),
			standBy(1),
			active(2)
			}
	    MAX-ACCESS  read-only
	    STATUS      current
	    DESCRIPTION
	        "This object indicates the primary port status of Flex Link pair."
	    ::= { swFlexLinkEntry 4 }

	swFlexLinkBackupStatus OBJECT-TYPE
	    SYNTAX      INTEGER{
			inActive(0),
			standBy(1),
			active(2)
			}
	    MAX-ACCESS  read-only
	    STATUS      current
	    DESCRIPTION
	        "This object indicates the backup port status of Flex Link pair."
	    ::= { swFlexLinkEntry 5 }

	swFlexLinkRowStatus OBJECT-TYPE
	    SYNTAX      RowStatus
	    MAX-ACCESS  read-create
	    STATUS      current
	    DESCRIPTION
	        "This object indicates the RowStatus of this entry."
	    ::= { swFlexLinkEntry 99 }
END
