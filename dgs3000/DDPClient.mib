-- -----------------------------------------------------------------------------
-- MIB NAME : DDP Client Common mib
-- FILE NAME: DDPClient.mib
-- DATE     : 2017/12/15
-- VERSION  : 1.01
-- PURPOSE  : To construct the MIB structure of D-Link Discovery Protocol Client 
--            for proprietary enterprise
-- -----------------------------------------------------------------------------
-- MODIFICTION HISTORY:
-- -----------------------------------------------------------------------------
-- Version, Date, Author
-- Description:
-- [New Object]
-- [Modification]
-- Notes: (Requested by who and which project)
-- -----------------------------------------------------------------------------  
-- Version 1.01, 2017/12/15, Morris Liao
-- Remove the DEFVAL because the default value should be project dependent
-- -----------------------------------------------------------------------------  
-- Version 1.00, 2017/08/14, Jean Chen
-- This is the first formal version for universal MIB definition.
-- -----------------------------------------------------------------------------  

DDP-CLIENT-MIB DEFINITIONS ::= BEGIN

	IMPORTS
	    MODULE-IDENTITY,OBJECT-TYPE     FROM SNMPv2-SMI
	    dlink-common-mgmt               FROM DLINK-ID-REC-MIB
        Unsigned32                      FROM SNMPv2-SMI
        TruthValue                      FROM SNMPv2-TC 
        ifIndex                         FROM IF-MIB;

	swDDPClientMIB MODULE-IDENTITY
	    LAST-UPDATED "1712150000Z"
	    ORGANIZATION "D-Link Corp."
	    CONTACT-INFO
	        "http://support.dlink.com"
	    DESCRIPTION
	        "The D-Link Discovery Protocol client module MIB for the proprietary enterprise."
	    ::= { dlink-common-mgmt 119}
 
    swDDPClientCtrl OBJECT IDENTIFIER ::= { swDDPClientMIB 1 }

    swDDPClientGlobalState  OBJECT-TYPE
        SYNTAX      TruthValue
        MAX-ACCESS  read-write
        STATUS      current
        DESCRIPTION
            "This object represents the DDP client's global state
                true - Indicates the DDP client is enabled
                false - Indicates the DDP client is disabled"
        ::= { swDDPClientCtrl 1 }

    swDDPClientReportTimer OBJECT-TYPE
        SYNTAX      Unsigned32 (0|30|60|90|120)
        UNITS       "second"
        MAX-ACCESS  read-write
        STATUS      current
        DESCRIPTION
            "This object specifies the interval at which DDP report messages are sent
            by the device.
            Setting the object to 0 prohibits the device from sending DDP report message."
        ::= { swDDPClientCtrl 2 }

    swDDPClientTable OBJECT-TYPE
        SYNTAX      SEQUENCE OF swDDPClientEntry
        MAX-ACCESS  not-accessible
        STATUS      current
        DESCRIPTION
            "The table contains a list of port-specific information for DDP client."
        ::= { swDDPClientCtrl 3 }

    swDDPClientEntry OBJECT-TYPE
        SYNTAX      swDDPClientEntry
        MAX-ACCESS  not-accessible
        STATUS      current
        DESCRIPTION
            "Each entry represents the DDP Client state on a port."
        INDEX       { ifIndex }
        ::= { swDDPClientTable 1 }

    swDDPClientEntry ::= SEQUENCE {
        swDDPClientPortState     TruthValue
    }

    swDDPClientPortState OBJECT-TYPE
        SYNTAX      TruthValue
        MAX-ACCESS  read-write
        STATUS      current
        DESCRIPTION
            "This object represents the DDP Client state on a port
                true - Indicates DDP client is enabled on the port
                false - Indicates DDP client is disabled on the port"
        ::= { swDDPClientEntry 1 }

END
