-- -----------------------------------------------------------------------------
-- MIB NAME : Access Authentication Control(AAC) Common mib
-- FILE NAME: AAC.mib
-- DATE     : 2014/11/18
-- VERSION  : 2.10
-- PURPOSE  : To construct the MIB structure of Access Authentication Control
--            for proprietary enterprise
-- -----------------------------------------------------------------------------
-- MODIFICTION HISTORY:
-- -----------------------------------------------------------------------------
-- Version, Date, Author
-- Description:
--  [New Object]
--  [Modification]
-- Notes: (Requested by who and which project)
--
-- Version 2.10, 2014/11/18, Shawn
-- [New Object]
-- 1. Added "swAACAcctNetworkMacAccounting",
-- to support accounting network traffic by MAC address.
--
-- Version 2.09, 2014/10/20, Leon
-- [New Object]
-- 1. Added "swAACRadiusServerAttr4Type", "swAACRadiusServerAttr4Address",
-- to support address for the RADIUS attribute 4 address.
--
-- Version 2.08, 2012/06/20, Shawn
-- [New Object]
-- 1. Added "swAACAcctCmdAdminLevelMethod", "swAACAcctCmdOperatorLevelMethod ",
-- "swAACAcctCmdPowerUserLevelMethod", "swAACAcctCmdUserLevelMethod"
-- to support command accounting.
--
-- Version 2.07, 2012/05/31, Shawn
-- [New Object]
-- 1. Added "swAACMaxAcctMethodList", "swAACAcctMethodListTable ", "swAACServerAcctPort ", "swAACIpv4ServerAcctPort",
-- "swAACAcctShellState", "swAACAcctSystemState", "swAACAcctNetworkState",
-- "swAACAcctShellMethod", "swAACAcctSystemMethod" and "swAACAcctNetworkMethod"
-- to support setting accounting server IP address separately.
-- [Modification]
-- 1. Rename "swAACServerGroupAuthProtocolX" to "swAACServerGroupSrvProtocolX" in swAACServerGroupTable
-- 2. Rename "swAACServerAuthProtocol" to "swAACServerProtocol", "swAACServerAuthKey" to "swAACServerKey" in swAACServerInfoTable
-- 3. Rename "swAACCtrlServerAuthProtocol" to "swAACCtrlServerProtocol" in swAACServerCtrlTable
-- 4. Rename "swAACIpv4ServerGroupAuthProtocolX" to "swAACIpv4ServerGroupProtocolX" in swAACIpv4ServerGroupTable
-- 5. Rename "swAACIpv4ServerAuthProtocol" to "swAACIpv4ServerProtocol", "swAACIpv4ServerAuthKey" to "swAACIpv4ServerKey" in swAACIpv4ServerInfoTable
-- 6. Rename "swAACIpv4CtrlServerAuthProtocol" to "swAACIpv4CtrlServerProtocol" in swAACIpv4ServerCtrlTable
-- 7. Rename "swAACAuthenEncryptionState" to "swAACSrvPwdEncryptionState" in swAACCtrl
-- 8. Modified description of above nodes. 
--
-- Version 2.06, 2012/04/07, Lillian
--  [New Object]
-- 1. Add "swAACServerGroupTable" and "swAACServerInfoTable" and "swAACServerCtrlTable" to support IPv6.
--  [Modification]
-- 2. Rename "swAACServerGroupTable","swAACServerInfoTable","swAACServerCtrlTable" to "swAACIpv4ServerGroupTable",
--      "swAACIpv4ServerInfoTable","swAACIpv4ServerCtrlTable".
--
-- Version 2.05, 2011/10/24, Shawn
--  [Modification]
-- 1. Change the syntax to INTEGER { enabled(1), disabled(2) } of the node "swAACAuthenEncryptionState".
--
-- Version 2.04, 2011/09/15, Shawn
--  [New Object]
-- 1.  Add "swAACCtrlEnableOperatorSet" to configure enable operator state of login authentication methods.
-- Notes: Requested by D-Link, DES3526/50 R6.
-- 2.  Add "swAACAuthenEncryptionState" to enable or disable authentication policy encryption.
-- 3.  Add "swAACServerGroupVrfName" in "swAACServerGroupTable" to support VRF function.
--
-- Version 2.03, 2009/01/21, Eli
--  [Modification]
--    Revise the range of "swAACServerAuthKey" to 0..254 from 0..255.
-- Notes: Requested by LAB, DES3200
--
-- Version 2.02, 2008/02/12, Ronald
--  [Modification]
--    To add the objects "swAACCtrlEnableAdminSet".
-- Notes: Requested by D-Link, DES3800
--
-- Version 2.01, 2007/04/30, Yedda
--  [Modification]
--    To recover the objects "swAACAPSSHLoginMethod" and "swAACAPSSHEnableMethod".
-- Notes: Requested by CD, DES3400
--
-- Version 2.00, 2007/03/27, Yedda
-- This is the first formal version for universal MIB definition.
-- -----------------------------------------------------------------------------

AAC-MIB DEFINITIONS ::= BEGIN

	IMPORTS
		IpAddress
	 		FROM RFC1155-SMI
	    MODULE-IDENTITY, OBJECT-TYPE
	        FROM SNMPv2-SMI
	    RowStatus,DisplayString
	        FROM SNMPv2-TC
	    MODULE-COMPLIANCE, OBJECT-GROUP
	        FROM SNMPv2-CONF
	    InetAddressType, InetAddress
	        FROM INET-ADDRESS-MIB

		dlink-common-mgmt	FROM DLINK-ID-REC-MIB;


	swAACMIB MODULE-IDENTITY
	    LAST-UPDATED "201411180000Z"
	    ORGANIZATION "D-Link Corp."
	    CONTACT-INFO
	        "http://support.dlink.com"
	    DESCRIPTION
	        "The Link AAC module MIB."
	    ::= { dlink-common-mgmt 5}

	swAACCtrl OBJECT IDENTIFIER ::= { swAACMIB 1 }
	swAACCtrlEnableAdminSet OBJECT IDENTIFIER ::= { swAACCtrl 2 }
	swAACCtrlEnableOperatorSet OBJECT IDENTIFIER ::= { swAACCtrl 3 }

-- -----------------------------------------------------------------------------
-- Textual Conventions
-- -----------------------------------------------------------------------------
	swAACAuthenAdminState OBJECT-TYPE
	    SYNTAX  INTEGER {
	                other(1),
	                disabled(2),
	                enabled(3)
	            }
	    MAX-ACCESS  read-write
	    STATUS  current
	    DESCRIPTION
	        "This object indicates if the Access Authentication is enabled or
	        disabled."
	    ::= { swAACCtrl 1}

	swAACSrvPwdEncryptionState OBJECT-TYPE
	    SYNTAX  INTEGER {
	                enabled(1),
	                disabled(2)
	            }
	    MAX-ACCESS  read-write
	    STATUS  current
	    DESCRIPTION
	        "This object indicates if the AAA server password encryption is enabled or
	        disabled."
	    ::= { swAACCtrl 4}
-- -----------------------------------------------------------------------------
-- swAACCtrlEnableAdminSet OBJECT IDENTIFIER ::= { swAACCtrl 2 }
-- -----------------------------------------------------------------------------
	swAACCtrlEnableAdminTACACSState OBJECT-TYPE
	    SYNTAX  INTEGER {
	                other(1),
	                disabled(2),
	                enabled(3)
	            }
	    MAX-ACCESS  read-write
	    STATUS  current
	    DESCRIPTION
	        "This object indicates if the state of TACACS is enabled or 
	        disabled."
	    ::= { swAACCtrlEnableAdminSet 1 }
	    
	swAACCtrlEnableAdminXTACACSState OBJECT-TYPE
	    SYNTAX  INTEGER {
	                other(1),
	                disabled(2),
	                enabled(3)
	            }
	    MAX-ACCESS  read-write
	    STATUS  current
	    DESCRIPTION
	        "This object indicates if the state of XTACACS is enabled or 
	        disabled."
	    ::= { swAACCtrlEnableAdminSet 2 }
	
	swAACCtrlEnableAdminTACACSPlusState OBJECT-TYPE
	    SYNTAX  INTEGER {
	                other(1),
	                disabled(2),
	                enabled(3)
	            }
	    MAX-ACCESS  read-write
	    STATUS  current
	    DESCRIPTION
	        "This object indicates if the state of TACACS+ is enabled or 
	        disabled."
	    ::= { swAACCtrlEnableAdminSet 3 }
	    
	swAACCtrlEnableAdminRadiusState OBJECT-TYPE
	    SYNTAX  INTEGER {
	                other(1),
	                disabled(2),
	                enabled(3)
	            }
	    MAX-ACCESS  read-write
	    STATUS  current
	    DESCRIPTION
	        "This object indicates if the state of Radius is enabled or 
	        disabled."
	    ::= { swAACCtrlEnableAdminSet 4 }
	    
	swAACCtrlEnableAdminLocalState OBJECT-TYPE
	    SYNTAX  INTEGER {
	                other(1),
	                disabled(2),
	                enabled(3)
	            }
	    MAX-ACCESS  read-write
	    STATUS  current
	    DESCRIPTION
	        "This object indicates if the state of Local is enabled or 
	        disabled."
	    ::= { swAACCtrlEnableAdminSet 5 }
	    
	swAACCtrlEnableAdminNoneState OBJECT-TYPE
	    SYNTAX  INTEGER {
	                other(1),
	                disabled(2),
	                enabled(3)
	            }
	    MAX-ACCESS  read-write
	    STATUS  current
	    DESCRIPTION
	        "This object indicates if the state of None is enabled or 
	        disabled."
	    ::= { swAACCtrlEnableAdminSet 6 }
-- -----------------------------------------------------------------------------
-- swAACCtrlEnableOperatorSet OBJECT IDENTIFIER ::= { swAACCtrl 3 }
-- -----------------------------------------------------------------------------
	swAACCtrlEnableOperatorTACACSState OBJECT-TYPE
	    SYNTAX  INTEGER {
	                enabled(1),
	                disabled(2)
	            }
	    MAX-ACCESS  read-write
	    STATUS  current
	    DESCRIPTION
	        "This object indicates if the (enable operator) state of TACACS is
	        enabled or disabled."
	    ::= { swAACCtrlEnableOperatorSet 1 }
	    
	swAACCtrlEnableOperatorXTACACSState OBJECT-TYPE
	    SYNTAX  INTEGER {
	                enabled(1),
	                disabled(2)
	            }
	    MAX-ACCESS  read-write
	    STATUS  current
	    DESCRIPTION
	        "This object indicates if the (enable operator) state of XTACACS is
	        enabled or disabled."
	    ::= { swAACCtrlEnableOperatorSet 2 }

	swAACCtrlEnableOperatorTACACSPlusState OBJECT-TYPE
	    SYNTAX  INTEGER {
	                enabled(1),
	                disabled(2)
	            }
	    MAX-ACCESS  read-write
	    STATUS  current
	    DESCRIPTION
	        "This object indicates if the (enable operator) state of TACACS+ is
	        enabled or disabled."
	    ::= { swAACCtrlEnableOperatorSet 3 }
	    
	swAACCtrlEnableOperatorRADIUSState OBJECT-TYPE
	    SYNTAX  INTEGER {
	                enabled(1),
	                disabled(2)
	            }
	    MAX-ACCESS  read-write
	    STATUS  current
	    DESCRIPTION
	        "This object indicates if the (enable operator) state of RADIUS is
	        enabled or disabled."
	    ::= { swAACCtrlEnableOperatorSet 4 }
	    
	swAACCtrlEnableOperatorLocalState OBJECT-TYPE
	    SYNTAX  INTEGER {
	                enabled(1),
	                disabled(2)
	            }
	    MAX-ACCESS  read-write
	    STATUS  current
	    DESCRIPTION
	        "This object indicates if the (enable operator) state of Local is
	        enabled or disabled."
	    ::= { swAACCtrlEnableOperatorSet 5 }
	    
	swAACCtrlEnableOperatorNoneState OBJECT-TYPE
	    SYNTAX  INTEGER {
	                enabled(1),
	                disabled(2)
	            }
	    MAX-ACCESS  read-write
	    STATUS  current
	    DESCRIPTION
	        "This object indicates if the (enable operator) state of None is
	        enabled or disabled."
	    ::= { swAACCtrlEnableOperatorSet 6 }

-- --------------------------------------------------------
-- Accounting Ctrl
-- --------------------------------------------------------
swAACAcctShellState OBJECT-TYPE
    SYNTAX	INTEGER {
			radius_only(1),
			acct_method(2),
			disabled(3)
    		}
    MAX-ACCESS  read-write
    STATUS      current
    DESCRIPTION
		"Specifies the status of the accounting service for shell events.
		radius_only(1): it indicates using 802.1X RADIUS servers in swRadiusServerTable for accounting services. 
		acct_method(2): it indicates using AAA method that configured in swAACAcctShellMethod for accounting services."
    DEFVAL {disabled}
    ::= { swAACCtrl 5 }

swAACAcctSystemState OBJECT-TYPE
    SYNTAX      INTEGER{
			radius_only(1),
			acct_method(2),
			disabled(3)
    		}
    MAX-ACCESS  read-write
    STATUS      current
    DESCRIPTION
		"Specifies the status of the accounting service for system events.
		radius_only(1): it indicates using 802.1X RADIUS servers in swRadiusServerTable for accounting services.
		acct_method(2): it indicates using AAA method that configured in swAACAcctSystemMethod for accounting services."
    DEFVAL {disabled}    
    ::= { swAACCtrl 6 }

swAACAcctNetworkState OBJECT-TYPE
    SYNTAX      INTEGER{
			radius_only(1),
			acct_method(2),
			disabled(3)
    		}
    MAX-ACCESS  read-write
    STATUS      current
    DESCRIPTION
		"Specifies the status of the accounting service for network access events.
		radius_only(1): it indicates using 802.1X RADIUS servers in swRadiusServerTable for accounting services.
		acct_method(2): it indicates using AAA method that configured in swAACAcctNetworkMethod for accounting services."
    DEFVAL {disabled}    
    ::= { swAACCtrl 7 }

swAACAcctShellMethod OBJECT-TYPE
	SYNTAX DisplayString(SIZE(1..15))
	MAX-ACCESS read-write
	STATUS current
	DESCRIPTION
		"Specifies the AAA accounting method for shell accounting service."
	::= { swAACCtrl 8 }

swAACAcctSystemMethod OBJECT-TYPE
	SYNTAX DisplayString(SIZE(1..15))
	MAX-ACCESS read-write
	STATUS current
	DESCRIPTION
		"Specifies the AAA accounting method for system accounting service."
	::= { swAACCtrl 9 }
	
swAACAcctNetworkMethod OBJECT-TYPE
	SYNTAX DisplayString(SIZE(1..15))
	MAX-ACCESS read-write
	STATUS current
	DESCRIPTION
		"Specifies the AAA accounting method for network accounting service."
	::= { swAACCtrl 10 }

swAACAcctCmdAdminLevelMethod OBJECT-TYPE
	SYNTAX DisplayString(SIZE(0..15))
	MAX-ACCESS read-write
	STATUS current
	DESCRIPTION
		"Specifies the AAA accounting method for all administrator level commands."
	::= { swAACCtrl 11 }

swAACAcctCmdOperatorLevelMethod OBJECT-TYPE
	SYNTAX DisplayString(SIZE(0..15))
	MAX-ACCESS read-write
	STATUS current
	DESCRIPTION
		"Specifies the AAA accounting method for all operator level commands."
	::= { swAACCtrl 12 }

swAACAcctCmdPowerUserLevelMethod OBJECT-TYPE
	SYNTAX DisplayString(SIZE(0..15))
	MAX-ACCESS read-write
	STATUS current
	DESCRIPTION
		"Specifies the AAA accounting method for all power user level commands."
	::= { swAACCtrl 13 }

swAACAcctCmdUserLevelMethod OBJECT-TYPE
	SYNTAX DisplayString(SIZE(0..15))
	MAX-ACCESS read-write
	STATUS current
	DESCRIPTION
		"Specifies the AAA accounting method for all user level commands."
	::= { swAACCtrl 14 }
	
-- --------------------------------------------------------
-- RADIUS Server Attribute 4
-- --------------------------------------------------------	
	
swAACRadiusServerAttr4Type OBJECT-TYPE
	SYNTAX      INTEGER{
		system_ip_address(1),
		connect_interface_ip_address(2),
		user_defined(3)
		}
	MAX-ACCESS read-write
	STATUS current
	DESCRIPTION
		"Specifies the IP address type for the RADIUS attribute 4 address.
		system_ip_address(1): Use System IP address as the RADIUS NAS-IP-Address attribute.
		connect_interface_ip_address(2): The RADIUS NAS-IP-Address attribute will be the 
		IP address on the interface that connects the network access server (NAS) to the RADIUS server.
		user_defined(3): Use user defined IP address as the RADIUS NAS-IP-Address attribute."
	::= { swAACCtrl 15 }
	
swAACRadiusServerAttr4Address OBJECT-TYPE
    SYNTAX  	IpAddress
    MAX-ACCESS  read-write
    STATUS  	current
    DESCRIPTION
    	"Specifies the IP address for the RADIUS attribute 4 address defined by user."
    ::= { swAACCtrl 16 }	

swAACAcctNetworkMacAccounting OBJECT-TYPE
	SYNTAX  INTEGER {
				other(1),
				disabled(2),
				enabled(3)
			}
	MAX-ACCESS  read-write
	STATUS  current
	DESCRIPTION
		"This object indicates the state of Accounting network traffic by MAC Address.
		Note: MAC-Accounting is project dependent feature, only a few projects support it."
	::= { swAACCtrl 17 }

-- -----------------------------------------------------------------------------
	swAACInfo OBJECT IDENTIFIER ::= { swAACMIB 2}

	swAACMaxLoginMethodList  OBJECT-TYPE
	    SYNTAX     INTEGER
	    MAX-ACCESS read-only
	    STATUS     current
	    DESCRIPTION
	        "The max number of Login method lists supported by the system ."
	    ::= { swAACInfo 1 }

	swAACMaxEnableMethodList  OBJECT-TYPE
	    SYNTAX     INTEGER
	    MAX-ACCESS read-only
	    STATUS     current
	    DESCRIPTION
	        "The max number of Enable method lists supported by the system ."
	    ::= { swAACInfo 2 }

	swAACMaxServerGroup  OBJECT-TYPE
	    SYNTAX     INTEGER
	    MAX-ACCESS read-only
	    STATUS     current
	    DESCRIPTION
	        "The max number of Server Group's supported by the system ."
	    ::= { swAACInfo 3 }

	swAACMaxServer  OBJECT-TYPE
	    SYNTAX     INTEGER
	    MAX-ACCESS read-only
	    STATUS     current
	    DESCRIPTION
	        "The max number of AAC servers supported by the system ."
	    ::= { swAACInfo 4 }

	swAACMaxAcctMethodList  OBJECT-TYPE
	    SYNTAX     INTEGER
	    MAX-ACCESS read-only
	    STATUS     current
	    DESCRIPTION
	        "The max number of accounting method lists supported by the system ."
	    ::= { swAACInfo 5 }

-- -----------------------------------------------------------------------------
-- Tables in the DLinkAAC MIB
-- -----------------------------------------------------------------------------

-- -----------------------------------------------------------------------------
-- Login Method list table
-- -----------------------------------------------------------------------------
	swAACLoginMethodListTable OBJECT-TYPE
	    SYNTAX SEQUENCE OF SwAACLoginMethodListEntry
	    MAX-ACCESS not-accessible
	    STATUS current
	    DESCRIPTION
	        "A table that contains information about Login authentication method
	        lists."

	    ::= { swAACMIB 3 }

	swAACLoginMethodListEntry OBJECT-TYPE
	    SYNTAX SwAACLoginMethodListEntry
	    MAX-ACCESS not-accessible
	    STATUS current
	    DESCRIPTION
	        "A list of the Authentication methods."
	    INDEX { swAACLoginMethodListName }

	    ::= { swAACLoginMethodListTable 1 }

	SwAACLoginMethodListEntry ::=
	    SEQUENCE {
	        swAACLoginMethodListName
	            DisplayString,
	        swAACLoginMethod1Type
	        	INTEGER,
	        swAACLoginMethod1ServerGroup
	            DisplayString,
	        swAACLoginMethod2Type
	        	INTEGER,
	        swAACLoginMethod2ServerGroup
	            DisplayString,
	        swAACLoginMethod3Type
	        	INTEGER,
	        swAACLoginMethod3ServerGroup
	            DisplayString,
	        swAACLoginMethod4Type
	        	INTEGER,
	        swAACLoginMethod4ServerGroup
	            DisplayString,
			swAACLoginMethodListRowStatus
				RowStatus

	    }

	swAACLoginMethodListName OBJECT-TYPE
	    SYNTAX DisplayString(SIZE(1..15))
	    MAX-ACCESS read-only
	    STATUS current
	    DESCRIPTION
	        "A human-readable text string of the method list. The string is the
	        same as swAACLoginMethodName."

	    ::= { swAACLoginMethodListEntry 1 }

	swAACLoginMethod1Type OBJECT-TYPE
	    SYNTAX INTEGER {
	                tacacs(1),
	                xtacacs(2),
	                tacacs-plus(3),
	                radius(4),
	                server-group(5),
	                local(6),
	                -- local-enable(7),
	                none(8),
	                other(9)
	            }
	    MAX-ACCESS read-create
	    STATUS current
	    DESCRIPTION
	        "The type of Login method list. The group type includes tacas(1),
	        xtacacs(2), tacacs-plus(3), radius(4) and server-group(5) for specific
	        users. The keyword type includes local(6), local-enable(7) and
	        none(8)."

	    ::= { swAACLoginMethodListEntry 2 }

	swAACLoginMethod1ServerGroup OBJECT-TYPE
	    SYNTAX DisplayString(SIZE(0..15))
	    MAX-ACCESS read-create
	    STATUS current
	    DESCRIPTION
	        "A human-readable text string of the server group. It would be null
	        as swAACLoginMethodListType is with the keyword type and it is writeable,
	        just as the swAACLoginMethodListType is in server_group(3)."

	    ::= { swAACLoginMethodListEntry 3 }

	swAACLoginMethod2Type OBJECT-TYPE
	    SYNTAX INTEGER {
	                tacacs(1),
	                xtacacs(2),
	                tacacs-plus(3),
	                radius(4),
	                server-group(5),
	                local(6),
	                -- local-enable(7),
	                none(8),
	                other(9)
	            }
	    MAX-ACCESS read-create
	    STATUS current
	    DESCRIPTION
	        "The type of Login method list. The group type includes tacas(1),
	        xtacacs(2), tacacs-plus(3), radius(4) and server-group(5) for specific 
		users. The keyword type includes local(6), local-enable(7) and
	        none(8)."

	    ::= { swAACLoginMethodListEntry 4 }

	swAACLoginMethod2ServerGroup OBJECT-TYPE
	    SYNTAX DisplayString(SIZE(0..15))
	    MAX-ACCESS read-create
	    STATUS current
	    DESCRIPTION
	        "A human-readable text string of the server group. It would be null
	        as swAACLoginMethodListType is with the keyword type and it is writeable,
	        just as the swAACLoginMethodListType is in server_group(3)."

	    ::= { swAACLoginMethodListEntry 5 }

	swAACLoginMethod3Type OBJECT-TYPE
	    SYNTAX INTEGER {
	                tacacs(1),
	                xtacacs(2),
	                tacacs-plus(3),
	                radius(4),
	                server-group(5),
	                local(6),
	                -- local-enable(7),
	                none(8),
	                other(9)
	            }
	    MAX-ACCESS read-create
	    STATUS current
	    DESCRIPTION
	        "The type of Login method list. The group type includes tacas(1),
	        xtacacs(2), tacacs-plus(3), radius(4) and server-group(5) for specific
		 users. The keyword type includes local(6), local-enable(7) and
	        none(8)."

	    ::= { swAACLoginMethodListEntry 6 }

	swAACLoginMethod3ServerGroup OBJECT-TYPE
	    SYNTAX DisplayString(SIZE(0..15))
	    MAX-ACCESS read-create
	    STATUS current
	    DESCRIPTION
	        "A human-readable text string of the server group. It would be null
	        as swAACLoginMethodListType is with the keyword type and It is writeable,
	        just as the swAACLoginMethodListType is in server_group(3)."

	    ::= { swAACLoginMethodListEntry 7 }

	swAACLoginMethod4Type OBJECT-TYPE
	    SYNTAX INTEGER {
	                tacacs(1),
	                xtacacs(2),
	                tacacs-plus(3),
	                radius(4),
	                server-group(5),
	                local(6),
	                -- local-enable(7),
	                none(8),
	                other(9)
	            }
	    MAX-ACCESS read-create
	    STATUS current
	    DESCRIPTION
	        "The type of Login method list. The group type includes tacas(1),
	        xtacacs(2), tacacs-plus(3), radius(4) and server-group(5) for specific
 		users. The keyword type includes local(6), local-enable(7), and
	        none(8)."

	    ::= { swAACLoginMethodListEntry 8 }

	swAACLoginMethod4ServerGroup OBJECT-TYPE
	    SYNTAX DisplayString(SIZE(0..15))
	    MAX-ACCESS read-create
	    STATUS current
	    DESCRIPTION
	        "A human-readable text string of the server group. It would be null
	        as swAACLoginMethodListType is for keyword type. And It is writeable,
	        just as the swAACLoginMethodListType is in server_group(3)."

	    ::= { swAACLoginMethodListEntry 9 }

	swAACLoginMethodListRowStatus OBJECT-TYPE
	    SYNTAX      RowStatus
	    MAX-ACCESS  read-create
	    STATUS      current
	    DESCRIPTION
	        "This object indicates the status of this entry. A set request with
	        RowStatus 'CreateAndGo' will fail when the current entry of
	        the table is equal to the maximum number of
	        swAACLoginMethodListIndex."

	    ::= { swAACLoginMethodListEntry 10 }

-- -----------------------------------------------------------------------------
-- Enable Method table
-- -----------------------------------------------------------------------------
	swAACEnableMethodListTable OBJECT-TYPE
	    SYNTAX SEQUENCE OF SwAACEnableMethodListEntry
	    MAX-ACCESS not-accessible
	    STATUS current
	    DESCRIPTION
	        "A table that contains information about Enable authentication method
	        lists."

	    ::= { swAACMIB 4 }

	swAACEnableMethodListEntry OBJECT-TYPE
	    SYNTAX SwAACEnableMethodListEntry
	    MAX-ACCESS not-accessible
	    STATUS current
	    DESCRIPTION
	        "A list of the Authentication methods."
	    INDEX { swAACEnableMethodListName }

	    ::= { swAACEnableMethodListTable 1 }

	SwAACEnableMethodListEntry ::=
	    SEQUENCE {
	        swAACEnableMethodListName
	            DisplayString,
	        swAACEnableMethod1Type
	        	INTEGER,
	        swAACEnableMethod1ServerGroup
	            DisplayString,
	        swAACEnableMethod2Type
	        	INTEGER,
	        swAACEnableMethod2ServerGroup
	            DisplayString,
	        swAACEnableMethod3Type
	        	INTEGER,
	        swAACEnableMethod3ServerGroup
	            DisplayString,
	        swAACEnableMethod4Type
	        	INTEGER,
	        swAACEnableMethod4ServerGroup
	            DisplayString,
			swAACEnableMethodListRowStatus
				RowStatus

	    }

	swAACEnableMethodListName OBJECT-TYPE
	    SYNTAX DisplayString(SIZE(1..15))
	    MAX-ACCESS read-only
	    STATUS current
	    DESCRIPTION
	        "A human-readable text string of the method list. The string is the
	        same as swAACEnableMethodName."

	    ::= { swAACEnableMethodListEntry 1 }

	swAACEnableMethod1Type OBJECT-TYPE
	    SYNTAX INTEGER {
	                tacacs(1),
	                xtacacs(2),
	                tacacs-plus(3),
	                radius(4),
	                server-group(5),
	                -- local(6),
	                local-enable(7),
	                none(8),
	                other(9)
	            }
	    MAX-ACCESS read-create
	    STATUS current
	    DESCRIPTION
	        "The type of Enable method list. The group type includes tacas(1),
	        xtacacs(2), tacacs-plus(3), radius(4) and server-group(5) for user
	        specific. The keyword type includes local(6), local-enable(7) and
	        none(8)."

	    ::= { swAACEnableMethodListEntry 2 }

	swAACEnableMethod1ServerGroup OBJECT-TYPE
	    SYNTAX DisplayString(SIZE(0..15))
	    MAX-ACCESS read-create
	    STATUS current
	    DESCRIPTION
	        "A human-readable text string of the server group. It would be null
	        as swAACEnableMethodListType is with the keyword type and it is writeable,
	        just as the swAACEnableMethodListType is in server_group(3)."

	    ::= { swAACEnableMethodListEntry 3 }

	swAACEnableMethod2Type OBJECT-TYPE
	    SYNTAX INTEGER {
	                tacacs(1),
	                xtacacs(2),
	                tacacs-plus(3),
	                radius(4),
	                server-group(5),
	                -- local(6),
	                local-enable(7),
	                none(8),
	                other(9)
	            }
	    MAX-ACCESS read-create
	    STATUS current
	    DESCRIPTION
	        "The type of Enable method list. The group type includes tacas(1),
	        xtacacs(2), tacacs-plus(3), radius(4) and server-group(5) for user
	        specific. The keyword type includes local(6), local-enable(7) and
	        none(8)."

	    ::= { swAACEnableMethodListEntry 4 }

	swAACEnableMethod2ServerGroup OBJECT-TYPE
	    SYNTAX DisplayString(SIZE(0..15))
	    MAX-ACCESS read-create
	    STATUS current
	    DESCRIPTION
	        "A human-readable text string of the server group. It would be null
	        as swAACEnableMethodListType is with the keyword type and it is writeable,
	        just as the swAACEnableMethodListType is in server_group(3)."

	    ::= { swAACEnableMethodListEntry 5 }

	swAACEnableMethod3Type OBJECT-TYPE
	    SYNTAX INTEGER {
	                tacacs(1),
	                xtacacs(2),
	                tacacs-plus(3),
	                radius(4),
	                server-group(5),
	                -- local(6),
	                local-enable(7),
	                none(8),
	                other(9)
	            }
	    MAX-ACCESS read-create
	    STATUS current
	    DESCRIPTION
	        "The type of Enable method list. The group type includes tacas(1),
	        xtacacs(2), tacacs-plus(3), radius(4) and server-group(5) for specific
		users. The keyword type includes local(6), local-enable(7) and
	        none(8)."

	    ::= { swAACEnableMethodListEntry 6 }

	swAACEnableMethod3ServerGroup OBJECT-TYPE
	    SYNTAX DisplayString(SIZE(0..15))
	    MAX-ACCESS read-create
	    STATUS current
	    DESCRIPTION
	        "A human-readable text string of the server group. It would be null
	        as swAACEnableMethodListType is for keyword type and it is writeable,
	        just as the swAACEnableMethodListType is in server_group(3)."

	    ::= { swAACEnableMethodListEntry 7 }

	swAACEnableMethod4Type OBJECT-TYPE
	    SYNTAX INTEGER {
	                tacacs(1),
	                xtacacs(2),
	                tacacs-plus(3),
	                radius(4),
	                server-group(5),
	                -- local(6),
	                local-enable(7),
	                none(8),
	                other(9)
	            }
	    MAX-ACCESS read-create
	    STATUS current
	    DESCRIPTION
	        "The type of Enable method list. The group type includes tacas(1),
	        xtacacs(2), tacacs-plus(3), radius(4) and server-group(5) for specific 
		users. The keyword type includes local(6), local-enable(7) and
	        none(8)."

	    ::= { swAACEnableMethodListEntry 8 }

	swAACEnableMethod4ServerGroup OBJECT-TYPE
	    SYNTAX DisplayString(SIZE(0..15))
	    MAX-ACCESS read-create
	    STATUS current
	    DESCRIPTION
	        "A human-readable text string of the server group. It would be null
	        as swAACEnableMethodListType is for keyword type and It is writeable,
	        just as the swAACEnableMethodListType is in server_group(3)."

	    ::= { swAACEnableMethodListEntry 9 }

	swAACEnableMethodListRowStatus OBJECT-TYPE
	    SYNTAX      RowStatus
	    MAX-ACCESS  read-create
	    STATUS      current
	    DESCRIPTION
	        "This object indicates the status of this entry. A set request with
	        RowStatus 'CreateAndGo' will fail when the current entry in
	        the table is equal to the maximum number of
	        swAACEnableMethodListIndex."

	    ::= { swAACEnableMethodListEntry 10 }


-- -----------------------------------------------------------------------------
-- Accounting Method table
-- -----------------------------------------------------------------------------
	swAACAcctMethodListTable OBJECT-TYPE
	    SYNTAX SEQUENCE OF SwAACAcctMethodListEntry
	    MAX-ACCESS not-accessible
	    STATUS current
	    DESCRIPTION
	        "A table that contains information about accounting method
	        lists."

	    ::= { swAACMIB 5 }

	swAACAcctMethodListEntry OBJECT-TYPE
	    SYNTAX SwAACAcctMethodListEntry
	    MAX-ACCESS not-accessible
	    STATUS current
	    DESCRIPTION
	        "A list of the accounting methods."
	    INDEX { swAACAcctMethodListName }
	    ::= { swAACAcctMethodListTable 1 }

	SwAACAcctMethodListEntry ::=
	    SEQUENCE {
	        swAACAcctMethodListName
	            DisplayString,
	        swAACAcctMethod1Type
	        	INTEGER,
	        swAACAcctMethod1ServerGroup
	            DisplayString,
	        swAACAcctMethod2Type
	        	INTEGER,
	        swAACAcctMethod2ServerGroup
	            DisplayString,
	        swAACAcctMethod3Type
	        	INTEGER,
	        swAACAcctMethod3ServerGroup
	            DisplayString,
	        swAACAcctMethod4Type
	        	INTEGER,
	        swAACAcctMethod4ServerGroup
	            DisplayString,
	        swAACAcctMethodListRowStatus
	        	RowStatus
	    }

	swAACAcctMethodListName OBJECT-TYPE
	    SYNTAX DisplayString(SIZE(1..15))
	    MAX-ACCESS read-only
	    STATUS current
	    DESCRIPTION
	        "A human-readable text string of the method list. The string is the
	        same as swAACAcctMethodName."
	    ::= { swAACAcctMethodListEntry 1 }

	swAACAcctMethod1Type OBJECT-TYPE
	    SYNTAX INTEGER {
	                tacacs-plus(1),
	                radius(2),
	                server-group(3),
	                none(4)
	            }
	    MAX-ACCESS read-create
	    STATUS current
	    DESCRIPTION
	        "The type of accounting method. The group type includes tacacs-plus(1),
	        radius(2) and server-group(3) for user specific. The keyword type 
	        includes none(4)."
	    ::= { swAACAcctMethodListEntry 2 }

	swAACAcctMethod1ServerGroup OBJECT-TYPE
	    SYNTAX DisplayString(SIZE(0..15))
	    MAX-ACCESS read-create
	    STATUS current
	    DESCRIPTION
	        "A human-readable text string of the server group. It would be null
	        as swAACAcctMethodListType is with the keyword type and it is writeable,
	        just as the swAACAcctMethodListType is in server_group(3)."
	    ::= { swAACAcctMethodListEntry 3 }

	swAACAcctMethod2Type OBJECT-TYPE
	    SYNTAX INTEGER {
	                tacacs-plus(1),
	                radius(2),
	                server-group(3),
	                none(4)
	            }
	    MAX-ACCESS read-create
	    STATUS current
	    DESCRIPTION
	        "The type of accounting method. The group type includes tacacs-plus(1),
	        radius(2) and server-group(3) for user specific. The keyword type 
	        includes none(4)."
	    ::= { swAACAcctMethodListEntry 4 }

	swAACAcctMethod2ServerGroup OBJECT-TYPE
	    SYNTAX DisplayString(SIZE(0..15))
	    MAX-ACCESS read-create
	    STATUS current
	    DESCRIPTION
	        "A human-readable text string of the server group. It would be null
	        as swAACAcctMethodListType is with the keyword type and it is writeable,
	        just as the swAACAcctMethodListType is in server_group(3)."
	    ::= { swAACAcctMethodListEntry 5 }

	swAACAcctMethod3Type OBJECT-TYPE
	    SYNTAX INTEGER {
	                tacacs-plus(1),
	                radius(2),
	                server-group(3),
	                none(4)
	            }
	    MAX-ACCESS read-create
	    STATUS current
	    DESCRIPTION
	        "The type of accounting method. The group type includes tacacs-plus(1),
	        radius(2) and server-group(3) for user specific. The keyword type 
	        includes none(4)."
	    ::= { swAACAcctMethodListEntry 6 }

	swAACAcctMethod3ServerGroup OBJECT-TYPE
	    SYNTAX DisplayString(SIZE(0..15))
	    MAX-ACCESS read-create
	    STATUS current
	    DESCRIPTION
	        "A human-readable text string of the server group. It would be null
	        as swAACAcctMethodListType is for keyword type and it is writeable,
	        just as the swAACAcctMethodListType is in server_group(3)."
	    ::= { swAACAcctMethodListEntry 7 }

	swAACAcctMethod4Type OBJECT-TYPE
	    SYNTAX INTEGER {
	                tacacs-plus(1),
	                radius(2),
	                server-group(3),
	                none(4)
	            }
	    MAX-ACCESS read-create
	    STATUS current
	    DESCRIPTION
	        "The type of accounting method. The group type includes tacacs-plus(1),
	        radius(2) and server-group(3) for user specific. The keyword type 
	        includes none(4)."
	    ::= { swAACAcctMethodListEntry 8 }

	swAACAcctMethod4ServerGroup OBJECT-TYPE
	    SYNTAX DisplayString(SIZE(0..15))
	    MAX-ACCESS read-create
	    STATUS current
	    DESCRIPTION
	        "A human-readable text string of the server group. It would be null
	        as swAACAcctMethodListType is for keyword type and It is writeable,
	        just as the swAACAcctMethodListType is in server_group(3)."
	    ::= { swAACAcctMethodListEntry 9 }

	swAACAcctMethodListRowStatus OBJECT-TYPE
	    SYNTAX      RowStatus
	    MAX-ACCESS  read-create
	    STATUS      current
	    DESCRIPTION
	        "This object indicates the status of this entry. A set request with
	        RowStatus 'CreateAndGo' will fail when the current entry in
	        the table is equal to the maximum number of
	        swAACAcctMethodListIndex."
	    ::= { swAACAcctMethodListEntry 10 }

-- -----------------------------------------------------------------------------
-- groups in the AAC MIB
-- swAACAPAuthMethodGroup OBJECT IDENTIFIER ::= { swAACMIB 7 }
-- -----------------------------------------------------------------------------
	swAACAPAuthMethodGroup OBJECT IDENTIFIER ::= { swAACMIB 7 }

	swAACAPLoginMethod OBJECT IDENTIFIER ::= { swAACAPAuthMethodGroup 1 }

	swAACAPEnableMethod OBJECT IDENTIFIER ::= { swAACAPAuthMethodGroup 2 }

	swAACAPConsoleLoginMethod OBJECT-TYPE
	    SYNTAX DisplayString(SIZE(1..15))
	    MAX-ACCESS read-write
	    STATUS current
	    DESCRIPTION
	        "Specifies the way to execute authentication when logging into the
	        system and the method for authentication.Access system via local
	        console"

	    ::= { swAACAPLoginMethod 1 }

	swAACAPTelnetLoginMethod OBJECT-TYPE
	    SYNTAX DisplayString(SIZE(1..15))
	    MAX-ACCESS read-write
	    STATUS current
	    DESCRIPTION
	        "Specifies the way to execute authentication when logging into the
	        system and the method for authentication.Access system via telnet."

	    ::= { swAACAPLoginMethod 2 }

    swAACAPSSHLoginMethod OBJECT-TYPE
	    SYNTAX DisplayString(SIZE(1..15))
	    MAX-ACCESS read-write
	    STATUS current
	    DESCRIPTION
	        "Specifies the way to execute authentication when logging into the
	        system and the method for authentication.Access system via SSH."

	    ::= { swAACAPLoginMethod 3 }

	swAACAPHttpLoginMethod OBJECT-TYPE
	    SYNTAX DisplayString(SIZE(1..15))
	    MAX-ACCESS read-write
	    STATUS current
	    DESCRIPTION
	        "Specifies the way to execute authentication when logging into the
	        system and the method for authentication.Access system via HTTP."

	    ::= { swAACAPLoginMethod 4 }

	swAACAPConsoleEnableMethod OBJECT-TYPE
	    SYNTAX DisplayString(SIZE(1..15))
	    MAX-ACCESS read-write
	    STATUS current
	    DESCRIPTION
	        "Specifies the way to execute authentication when logging into the
	        system and the method for authentication.Access system via local
	        console."
	    ::= { swAACAPEnableMethod 1 }

	swAACAPTelnetEnableMethod OBJECT-TYPE
	    SYNTAX DisplayString(SIZE(1..15))
	    MAX-ACCESS read-write
	    STATUS current
	    DESCRIPTION
	        "Specifies the way to execute authentication when logging into the
	        system and the method for authentication.Access system via telnet."

	    ::= { swAACAPEnableMethod 2 }

	swAACAPSSHEnableMethod OBJECT-TYPE
	    SYNTAX DisplayString(SIZE(1..15))
	    MAX-ACCESS read-write
	    STATUS current
	    DESCRIPTION
	        "Specifies the way to execute authentication when logging into the
	        system and the method for authentication.Access system via SSH."

	    ::= { swAACAPEnableMethod 3 }

	swAACAPHttpEnableMethod OBJECT-TYPE
	    SYNTAX DisplayString(SIZE(1..15))
	    MAX-ACCESS read-write
	    STATUS current
	    DESCRIPTION
	        "Specifies the way to execute authentication when logging into the
	        system and the method for authentication.Access system via HTTP."

	    ::= { swAACAPEnableMethod 4 }

-- -----------------------------------------------------------------------------
-- swAACAPAuthParamGroup OBJECT IDENTIFIER ::= { swAACMIB 8 }
-- -----------------------------------------------------------------------------
	swAACAuthParamGroup OBJECT IDENTIFIER ::= { swAACMIB 8 }

	swAACAuthParamResponseTimeout  OBJECT-TYPE
		    SYNTAX     INTEGER (0..255)
		    MAX-ACCESS read-write
		    STATUS     current
		    DESCRIPTION
		        "Timeout in seconds for login authentication response."
		    ::= { swAACAuthParamGroup 1 }

	swAACAuthParamAttempt  OBJECT-TYPE
		    SYNTAX     INTEGER (1..255)
		    MAX-ACCESS read-write
		    STATUS     current
		    DESCRIPTION
		        "The amount of login authentication attempts, if login failure 
			 exceeds, connection or access will be locked."
		    ::= { swAACAuthParamGroup 2 }

-- -----------------------------------------------------------------------------
-- swAACIpv4ServerGroup OBJECT IDENTIFIER ::= { swAACMIB 9 }
-- -----------------------------------------------------------------------------
	swAACIpv4ServerGroupTable OBJECT-TYPE
	    SYNTAX SEQUENCE OF SwAACIpv4ServerGroupEntry
	    MAX-ACCESS not-accessible
	    STATUS current
	    DESCRIPTION
	        "A table that contains information about a server group."
	    ::= { swAACMIB 9 }

	swAACIpv4ServerGroupEntry OBJECT-TYPE
	    SYNTAX SwAACIpv4ServerGroupEntry
	    MAX-ACCESS not-accessible
	    STATUS current
	    DESCRIPTION
	        "A list of the groups including servers."
	    INDEX { swAACIpv4ServerGroupName }
	    ::= { swAACIpv4ServerGroupTable 1 }

	SwAACIpv4ServerGroupEntry ::=
	    SEQUENCE {
	        swAACIpv4ServerGroupName
	            DisplayString,
			swAACIpv4ServerGroupIPAddr1
				IpAddress,
			swAACIpv4ServerGroupProtocol1
				INTEGER,
			swAACIpv4ServerGroupIPAddr2
				IpAddress,
			swAACIpv4ServerGroupProtocol2
				INTEGER,
			swAACIpv4ServerGroupIPAddr3
				IpAddress,
			swAACIpv4ServerGroupProtocol3
				INTEGER,
			swAACIpv4ServerGroupIPAddr4
				IpAddress,
			swAACIpv4ServerGroupProtocol4
				INTEGER,
			swAACIpv4ServerGroupIPAddr5
				IpAddress,
			swAACIpv4ServerGroupProtocol5
				INTEGER,
			swAACIpv4ServerGroupIPAddr6
				IpAddress,
			swAACIpv4ServerGroupProtocol6
				INTEGER,
			swAACIpv4ServerGroupIPAddr7
				IpAddress,
			swAACIpv4ServerGroupProtocol7
				INTEGER,
			swAACIpv4ServerGroupIPAddr8
				IpAddress,
			swAACIpv4ServerGroupProtocol8
				INTEGER,
	        swAACIpv4ServerGroupRowStatus
	            RowStatus,
			swAACIpv4ServerGroupVrfName
				DisplayString
	    }

	swAACIpv4ServerGroupName OBJECT-TYPE
	    SYNTAX DisplayString(SIZE(1..15))
	    MAX-ACCESS read-only
	    STATUS current
	    DESCRIPTION
	        "A human-readable text string of the method group."

	    ::= { swAACIpv4ServerGroupEntry 1 }


	swAACIpv4ServerGroupIPAddr1 OBJECT-TYPE
	    SYNTAX      IpAddress
	    MAX-ACCESS  read-only
	    STATUS      current
	    DESCRIPTION
	        "The IP address of Server"

	    ::= { swAACIpv4ServerGroupEntry 2 }

	swAACIpv4ServerGroupProtocol1 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 3 }

	swAACIpv4ServerGroupIPAddr2 OBJECT-TYPE
	    SYNTAX      IpAddress
	    MAX-ACCESS  read-only
	    STATUS      current
	    DESCRIPTION
	        "The IP address of Server"

	    ::= { swAACIpv4ServerGroupEntry 4 }

	swAACIpv4ServerGroupProtocol2 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 5 }

	swAACIpv4ServerGroupIPAddr3 OBJECT-TYPE
	    SYNTAX      IpAddress
	    MAX-ACCESS  read-only
	    STATUS      current
	    DESCRIPTION
	        "The IP address of Server"

	    ::= { swAACIpv4ServerGroupEntry 6 }

	swAACIpv4ServerGroupProtocol3 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 7 }

	swAACIpv4ServerGroupIPAddr4 OBJECT-TYPE
	    SYNTAX      IpAddress
	    MAX-ACCESS  read-only
	    STATUS      current
	    DESCRIPTION
	        "The IP address of the Server"

	    ::= { swAACIpv4ServerGroupEntry 8 }

	swAACIpv4ServerGroupProtocol4 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 9 }

	swAACIpv4ServerGroupIPAddr5 OBJECT-TYPE
	    SYNTAX      IpAddress
	    MAX-ACCESS  read-only
	    STATUS      current
	    DESCRIPTION
	        "The IP address of the Server"

	    ::= { swAACIpv4ServerGroupEntry 10 }

	swAACIpv4ServerGroupProtocol5 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 11 }

	swAACIpv4ServerGroupIPAddr6 OBJECT-TYPE
	    SYNTAX      IpAddress
	    MAX-ACCESS  read-only
	    STATUS      current
	    DESCRIPTION
	        "The IP address of the Server"

	    ::= { swAACIpv4ServerGroupEntry 12 }

	swAACIpv4ServerGroupProtocol6 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 13 }

	swAACIpv4ServerGroupIPAddr7 OBJECT-TYPE
	    SYNTAX      IpAddress
	    MAX-ACCESS  read-only
	    STATUS      current
	    DESCRIPTION
	        "The IP address of Server"

	    ::= { swAACIpv4ServerGroupEntry 14 }

	swAACIpv4ServerGroupProtocol7 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 15 }

	swAACIpv4ServerGroupIPAddr8 OBJECT-TYPE
	    SYNTAX      IpAddress
	    MAX-ACCESS  read-only
	    STATUS      current
	    DESCRIPTION
	        "The IP address of Server"

	    ::= { swAACIpv4ServerGroupEntry 16 }

	swAACIpv4ServerGroupProtocol8 OBJECT-TYPE
	    SYNTAX      INTEGER{
	    				tacacs(1),
	                    xtacacs(2),
	                    tacacs-plus(3),
	                    radius(4),
	                    none(5),
	                    other(6)
	                }
	    MAX-ACCESS  read-only
	    STATUS      current
	    DESCRIPTION
	        "The protocol provided by the Server."

	    ::= { swAACIpv4ServerGroupEntry 17 }

	swAACIpv4ServerGroupRowStatus	OBJECT-TYPE
	    SYNTAX      RowStatus
	    MAX-ACCESS  read-create
	    STATUS      current
	    DESCRIPTION
	        "This object indicates the status of this entry. A set request with 
		RowStatus 'CreateAndGo' will fail when the current entry in the table 
		is equal to swAACMaxServerGroup. "

	    ::= { swAACIpv4ServerGroupEntry 18 }

	swAACIpv4ServerGroupVrfName OBJECT-TYPE
	    SYNTAX DisplayString(SIZE(0..12))
	    MAX-ACCESS read-write
	    STATUS current
	    DESCRIPTION
	        "This object is used to add or remove the VRF for AAA server group"

	    ::= { swAACIpv4ServerGroupEntry 19 }

-- -----------------------------------------------------------------------------
-- swAACIpv4ServerInfo OBJECT IDENTIFIER ::= { swAACMIB 10 }
-- -----------------------------------------------------------------------------
	swAACIpv4ServerInfoTable OBJECT-TYPE
	    SYNTAX SEQUENCE OF SwAACIpv4ServerInfoEntry
	    MAX-ACCESS not-accessible
	    STATUS current
	    DESCRIPTION
	        "A table that contains information about severs."
	    ::= { swAACMIB 10 }

	swAACIpv4ServerInfoEntry OBJECT-TYPE
	    SYNTAX SwAACIpv4ServerInfoEntry
	    MAX-ACCESS not-accessible
	    STATUS current
	    DESCRIPTION
	        "A list of the information of server ."
	    INDEX { swAACIpv4ServerIPAddr,swAACIpv4ServerProtocol }
	    ::= { swAACIpv4ServerInfoTable 1 }

	SwAACIpv4ServerInfoEntry ::=
	    SEQUENCE {
			swAACIpv4ServerIPAddr
				IpAddress,
			swAACIpv4ServerProtocol
				INTEGER,
			swAACIpv4ServerAuthPort
				INTEGER,
			swAACIpv4ServerKey
				DisplayString,
	        swAACIpv4ServerTimeout
	            INTEGER,
	        swAACIpv4ServerRetryCount
	            INTEGER,
	        swAACIpv4ServerRowStatus
	            RowStatus,
	        swAACIpv4ServerAcctPort
	            INTEGER
		}

	swAACIpv4ServerIPAddr OBJECT-TYPE
	    SYNTAX      IpAddress
	    MAX-ACCESS  read-only
	    STATUS      current
	    DESCRIPTION
	        "The IP address of Server"
	    ::= { swAACIpv4ServerInfoEntry 1 }

	swAACIpv4ServerProtocol OBJECT-TYPE
	    SYNTAX      INTEGER{
	                    tacacs(1),
	                    xtacacs(2),
	                    tacacs-plus(3),
	                    radius(4)
	                }
	    MAX-ACCESS  read-only
	    STATUS      current
	    DESCRIPTION
	        "The protocol provided by the Server."
	    ::= { swAACIpv4ServerInfoEntry 2 }

	swAACIpv4ServerAuthPort OBJECT-TYPE
	    SYNTAX      INTEGER(1..65535)
	    MAX-ACCESS  read-create
	    STATUS      current
	    DESCRIPTION
	        "The TCP/IP port. The default authentication port is 49 and port numbers
	        5001 to 65535 are valid settings in the system , other values, except
	        49,5001-65535 will work when set in this object."
	    ::= { swAACIpv4ServerInfoEntry 3 }

	swAACIpv4ServerKey OBJECT-TYPE
	    SYNTAX DisplayString(SIZE(0..254))
	    MAX-ACCESS read-create
	    STATUS current
	    DESCRIPTION
			"The key pre-negotiated between NAS and server. 
			It is used to encrypt user's authentication data before being transmitted over internet.
			It is write-only."

	    ::= { swAACIpv4ServerInfoEntry 4 }

	swAACIpv4ServerTimeout OBJECT-TYPE
	    SYNTAX      INTEGER(1..255)
	    MAX-ACCESS  read-create
	    STATUS      current
	    DESCRIPTION
	        "Server response timeout ."
	    ::= { swAACIpv4ServerInfoEntry 5 }

	swAACIpv4ServerRetryCount OBJECT-TYPE
	    SYNTAX      INTEGER(1..255)
	    MAX-ACCESS  read-create
	    STATUS      current
	    DESCRIPTION
	        "The client retry count ."
	    ::= { swAACIpv4ServerInfoEntry 6 }

	swAACIpv4ServerRowStatus OBJECT-TYPE
	    SYNTAX      RowStatus
	    MAX-ACCESS  read-create
	    STATUS      current
	    DESCRIPTION
	        "This object indicates the status of this entry. A set request with
	        RowStatus 'CreateAndGo' will fail when the current entry in
	        the table is equal to swAACMaxServer. "
	    ::= { swAACIpv4ServerInfoEntry 7 }

	swAACIpv4ServerAcctPort OBJECT-TYPE
	    SYNTAX      INTEGER(1..65535)
	    MAX-ACCESS  read-create
	    STATUS      current
	    DESCRIPTION
			"The UDP port. The default accounting port for RADIUS server is 1813.
			This value is meaningless for TACACS, XTACACS, TACACS PLUS"
	    ::= { swAACIpv4ServerInfoEntry 8 }

-- -----------------------------------------------------------------------------
-- swAACIpv4ServerGroupCtrl OBJECT IDENTIFIER ::= { swAACMIB 12 }
-- -----------------------------------------------------------------------------
	swAACIpv4ServerCtrlTable OBJECT-TYPE
	    SYNTAX SEQUENCE OF SwAACIpv4ServerCtrlEntry
	    MAX-ACCESS not-accessible
	    STATUS current
	    DESCRIPTION
	        "A table that is used to add/delete a server from the group."
	    ::= { swAACMIB 12 }

	swAACIpv4ServerCtrlEntry OBJECT-TYPE
	    SYNTAX SwAACIpv4ServerCtrlEntry
	    MAX-ACCESS not-accessible
	    STATUS current
	    DESCRIPTION
	        "A table that is used to add/delete a server from group."
	    INDEX { swAACIpv4CtrlServerGroupName,swAACIpv4CtrlServerIPAddr,swAACIpv4CtrlServerProtocol }
	    ::= { swAACIpv4ServerCtrlTable 1 }

	SwAACIpv4ServerCtrlEntry ::=
	    SEQUENCE {
	    	swAACIpv4CtrlServerGroupName
	    		DisplayString,
	    	swAACIpv4CtrlServerIPAddr
	    		IpAddress,
	    	swAACIpv4CtrlServerProtocol
	    		INTEGER,
	        swAACIpv4CtrlServerRowState
	            INTEGER
	    }

	swAACIpv4CtrlServerGroupName OBJECT-TYPE
	    SYNTAX      DisplayString(SIZE(1..15))
	    MAX-ACCESS  not-accessible
	    STATUS      current
	    DESCRIPTION
	        "A human-readable text string of the method group."
	    ::= { swAACIpv4ServerCtrlEntry 1 }

	swAACIpv4CtrlServerIPAddr OBJECT-TYPE
	    SYNTAX      IpAddress
	    MAX-ACCESS  not-accessible
	    STATUS      current
	    DESCRIPTION
	        "The IP address of the Server"
	    ::= { swAACIpv4ServerCtrlEntry 2 }

	swAACIpv4CtrlServerProtocol OBJECT-TYPE
	    SYNTAX      INTEGER{
	                    tacacs(1),
	                    xtacacs(2),
	                    tacacs-plus(3),
	                    radius(4)
	                }
	    MAX-ACCESS  not-accessible
	    STATUS      current
	    DESCRIPTION
	        "The protocol provided by the Server."
	    ::= { swAACIpv4ServerCtrlEntry 3 }

	swAACIpv4CtrlServerRowState OBJECT-TYPE
	    SYNTAX      INTEGER{
	                    add(1),
	                    delete(2)
	                }
	    MAX-ACCESS  read-write
	    STATUS      current
	    DESCRIPTION
	        "This object is used to add or delete an entry from swAACIpv4ServerGroupTable."
	    ::= { swAACIpv4ServerCtrlEntry 4 }

-- -----------------------------------------------------------------------------
-- swAACServerGroup OBJECT IDENTIFIER ::= { swAACMIB 13 }
-- -----------------------------------------------------------------------------
	swAACServerGroupTable OBJECT-TYPE
		SYNTAX SEQUENCE OF SwAACServerGroupEntry
		MAX-ACCESS not-accessible
		STATUS current
		DESCRIPTION
			"A table that contains information about a server group."
		::= { swAACMIB 13 }

	swAACServerGroupEntry OBJECT-TYPE
		SYNTAX SwAACServerGroupEntry
		MAX-ACCESS not-accessible
		STATUS current
		DESCRIPTION
			"A list of the groups including servers."
		INDEX { swAACServerGroupName }
		::= { swAACServerGroupTable 1 }

	SwAACServerGroupEntry ::=
		SEQUENCE {
			swAACServerGroupName
				DisplayString,
			swAACServerGroupAddrType1
				InetAddressType,
			swAACServerGroupIPAddr1
				InetAddress,
			swAACServerGroupSrvProtocol1
				INTEGER,
			swAACServerGroupAddrType2
				InetAddressType,
			swAACServerGroupIPAddr2
				InetAddress,
			swAACServerGroupSrvProtocol2
				INTEGER,
			swAACServerGroupAddrType3
				InetAddressType,
			swAACServerGroupIPAddr3
				InetAddress,
			swAACServerGroupSrvProtocol3
				INTEGER,
			swAACServerGroupAddrType4
				InetAddressType,
			swAACServerGroupIPAddr4
				InetAddress,
			swAACServerGroupSrvProtocol4
				INTEGER,
			swAACServerGroupAddrType5
				InetAddressType,
			swAACServerGroupIPAddr5
				InetAddress,
			swAACServerGroupSrvProtocol5
				INTEGER,
			swAACServerGroupAddrType6
				InetAddressType,
			swAACServerGroupIPAddr6
				InetAddress,
			swAACServerGroupSrvProtocol6
				INTEGER,
			swAACServerGroupAddrType7
				InetAddressType,
			swAACServerGroupIPAddr7
				InetAddress,
			swAACServerGroupSrvProtocol7
				INTEGER,
			swAACServerGroupAddrType8
				InetAddressType,
			swAACServerGroupIPAddr8
				InetAddress,
			swAACServerGroupSrvProtocol8
				INTEGER,
			swAACServerGroupVrfName
				DisplayString,
			swAACServerGroupRowStatus
				RowStatus
		}

	swAACServerGroupName OBJECT-TYPE
		SYNTAX DisplayString(SIZE(1..15))
		MAX-ACCESS read-only
		STATUS current
		DESCRIPTION
			"A human-readable text string of the method group."
		::= { swAACServerGroupEntry 1 }

	swAACServerGroupAddrType1 OBJECT-TYPE
		SYNTAX		  InetAddressType
		MAX-ACCESS	  read-only
		STATUS		  current
		DESCRIPTION
			"The type of Server IP address.Only support ipv4(1) and ipv6(2)."
		::= { swAACServerGroupEntry 2 }

	swAACServerGroupIPAddr1	OBJECT-TYPE
		SYNTAX		InetAddress
		MAX-ACCESS	read-only
		STATUS		current
		DESCRIPTION
			"The IP address of server."
		::= { swAACServerGroupEntry 3 }

	swAACServerGroupSrvProtocol1 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 4 }

	swAACServerGroupAddrType2 OBJECT-TYPE
		SYNTAX		  InetAddressType
		MAX-ACCESS	  read-only
		STATUS		  current
		DESCRIPTION
			"The type of Server IP address.Only support ipv4(1) and ipv6(2)."
		::= { swAACServerGroupEntry 5 }

	swAACServerGroupIPAddr2	OBJECT-TYPE
		SYNTAX		InetAddress
		MAX-ACCESS	read-only
		STATUS		current
		DESCRIPTION
			"The IP address of server."
		::= {swAACServerGroupEntry 6 }

	swAACServerGroupSrvProtocol2 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 7 }

	swAACServerGroupAddrType3 OBJECT-TYPE
		SYNTAX		  InetAddressType
		MAX-ACCESS	  read-only
		STATUS		  current
		DESCRIPTION
			"The type of Server IP address.Only support ipv4(1) and ipv6(2)."
		::= { swAACServerGroupEntry 8 }

	swAACServerGroupIPAddr3	OBJECT-TYPE
		SYNTAX		InetAddress
		MAX-ACCESS	read-only
		STATUS		current
		DESCRIPTION
			"The IP address of server."
		::= {swAACServerGroupEntry 9 }

	swAACServerGroupSrvProtocol3 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 10 }

	swAACServerGroupAddrType4 OBJECT-TYPE
		SYNTAX		  InetAddressType
		MAX-ACCESS	  read-only
		STATUS		  current
		DESCRIPTION
			"The type of Server IP address.Only support ipv4(1) and ipv6(2)."
		::= { swAACServerGroupEntry 11 }

	swAACServerGroupIPAddr4	OBJECT-TYPE
		SYNTAX		InetAddress
		MAX-ACCESS	read-only
		STATUS		current
		DESCRIPTION
			"The IP address of server."
		::= {swAACServerGroupEntry 12 }

	swAACServerGroupSrvProtocol4 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 13 }

	swAACServerGroupAddrType5 OBJECT-TYPE
		SYNTAX		  InetAddressType
		MAX-ACCESS	  read-only
		STATUS		  current
		DESCRIPTION
			"The type of Server IP address.Only support ipv4(1) and ipv6(2)."
		::= { swAACServerGroupEntry 14 }

	swAACServerGroupIPAddr5	OBJECT-TYPE
		SYNTAX		InetAddress
		MAX-ACCESS	read-only
		STATUS		current
		DESCRIPTION
			"The IP address of server."

		::= {swAACServerGroupEntry 15 }

	swAACServerGroupSrvProtocol5 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 16 }

	swAACServerGroupAddrType6 OBJECT-TYPE
		SYNTAX		  InetAddressType
		MAX-ACCESS	  read-only
		STATUS		  current
		DESCRIPTION
			"The type of Server IP address.Only support ipv4(1) and ipv6(2)."
		::= { swAACServerGroupEntry 17 }

	swAACServerGroupIPAddr6	OBJECT-TYPE
		SYNTAX		InetAddress
		MAX-ACCESS	read-only
		STATUS		current
		DESCRIPTION
			"The IP address of server."
		::= {swAACServerGroupEntry 18 }

	swAACServerGroupSrvProtocol6 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 19 }

	swAACServerGroupAddrType7 OBJECT-TYPE
		SYNTAX		  InetAddressType
		MAX-ACCESS	  read-only
		STATUS		  current
		DESCRIPTION
			"The type of Server IP address.Only support ipv4(1) and ipv6(2)."
		::= { swAACServerGroupEntry 20 }

	swAACServerGroupIPAddr7	OBJECT-TYPE
		SYNTAX		InetAddress
		MAX-ACCESS	read-only
		STATUS		current
		DESCRIPTION
			"The IP address of server."
		::= {swAACServerGroupEntry 21 }

	swAACServerGroupSrvProtocol7 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 22 }

	swAACServerGroupAddrType8 OBJECT-TYPE
		SYNTAX		  InetAddressType
		MAX-ACCESS	  read-only
		STATUS		  current
		DESCRIPTION
			"The type of Server IP address.Only support ipv4(1) and ipv6(2)."
		::= { swAACServerGroupEntry 23 }

	swAACServerGroupIPAddr8	OBJECT-TYPE
		SYNTAX		InetAddress
		MAX-ACCESS	read-only
		STATUS		current
		DESCRIPTION
			"The IP address of server."
		::= {swAACServerGroupEntry 24 }

	swAACServerGroupSrvProtocol8 OBJECT-TYPE
		SYNTAX      INTEGER{
			tacacs(1),
			xtacacs(2),
			tacacs-plus(3),
			radius(4),
			none(5),
			other(6)
		}
		MAX-ACCESS  read-only
		STATUS      current
		DESCRIPTION
			"The protocol provided by the Server."
		::= { swAACServerGroupEntry 25 }

	swAACServerGroupVrfName OBJECT-TYPE
		SYNTAX DisplayString(SIZE(0..12))
		MAX-ACCESS read-write
		STATUS current
		DESCRIPTION
			"This object is used to add or remove the VRF for AAA server group"
		::= { swAACServerGroupEntry 26 }

	swAACServerGroupRowStatus	OBJECT-TYPE
		SYNTAX      RowStatus
		MAX-ACCESS  read-create
		STATUS      current
		DESCRIPTION
			"This object indicates the status of this entry. A set request with
			RowStatus 'CreateAndGo' will fail when the current entry in the table
			is equal to swAACMaxServerGroup. "
		::= { swAACServerGroupEntry 50 }

-- -----------------------------------------------------------------------------
-- swAACServerInfo OBJECT IDENTIFIER ::= { swAACMIB 14 }
-- -----------------------------------------------------------------------------
		swAACServerInfoTable OBJECT-TYPE
		SYNTAX SEQUENCE OF SwAACServerInfoEntry
		MAX-ACCESS not-accessible
		STATUS current
		DESCRIPTION
			"A table that contains information about severs."
		::= { swAACMIB 14 }

	swAACServerInfoEntry OBJECT-TYPE
		SYNTAX SwAACServerInfoEntry
		MAX-ACCESS not-accessible
		STATUS current
		DESCRIPTION
			"A list of the information of server."
		INDEX { swAACServerAddrType, swAACServerIPAddr,swAACServerProtocol }
		::= { swAACServerInfoTable 1 }

	SwAACServerInfoEntry ::=
		SEQUENCE {
			swAACServerAddrType
				InetAddressType,
			swAACServerIPAddr
				InetAddress,
			swAACServerProtocol
				INTEGER,
			swAACServerAuthPort
				INTEGER,
			swAACServerAcctPort
				INTEGER,
			swAACServerKey
				DisplayString,
			swAACServerTimeout
				INTEGER,
			swAACServerRetryCount
				INTEGER,
			swAACServerRowStatus
				RowStatus
		}

	swAACServerAddrType OBJECT-TYPE
		SYNTAX		  InetAddressType
		MAX-ACCESS	  read-only
		STATUS		  current
		DESCRIPTION
			"The type of Server IP address.Only support ipv4(1) and ipv6(2)."
		::= { swAACServerInfoEntry 1 }

	swAACServerIPAddr OBJECT-TYPE
		SYNTAX      InetAddress
		MAX-ACCESS  read-only
		STATUS      current
		DESCRIPTION
			"The IP address of Server."
		::= { swAACServerInfoEntry 2 }

	swAACServerProtocol OBJECT-TYPE
		SYNTAX      INTEGER{
			tacacs(1),
			xtacacs(2),
			tacacs-plus(3),
			radius(4)
		}
		MAX-ACCESS  read-only
		STATUS      current
		DESCRIPTION
			"The protocol provided by the Server."
		::= { swAACServerInfoEntry 3 }


	swAACServerAuthPort OBJECT-TYPE
		SYNTAX      INTEGER(1..65535)
		MAX-ACCESS  read-create
		STATUS      current
		DESCRIPTION
			"The TCP/IP port. The default authentication port for TACACS server and XTACACS server 
			and TACACS PLUS server is 49, and the default authentication port for RADIUS server is 
			1812."
		::= { swAACServerInfoEntry 4 }

	swAACServerAcctPort OBJECT-TYPE
		SYNTAX      INTEGER(1..65535)
		MAX-ACCESS  read-create
		STATUS      current
		DESCRIPTION
			"The UDP port. The default accounting port for RADIUS server is 1813.
			This value is meaningless for TACACS, XTACACS, TACACS PLUS"
		::= { swAACServerInfoEntry 5 }

	swAACServerKey OBJECT-TYPE
		SYNTAX DisplayString(SIZE(0..254))
		MAX-ACCESS read-create
		STATUS current
		DESCRIPTION
			"The key pre-negotiated between NAS and server. 
			It is used to encrypt user's authentication data before being transmitted over internet.
			It is write-only."
		::= { swAACServerInfoEntry 6 }

	swAACServerTimeout OBJECT-TYPE
		SYNTAX      INTEGER(1..255)
		MAX-ACCESS  read-create
		STATUS      current
		DESCRIPTION
			"Server response timeout."
		::= { swAACServerInfoEntry 7 }

	swAACServerRetryCount OBJECT-TYPE
		SYNTAX      INTEGER(1..20)
		MAX-ACCESS  read-create
		STATUS      current
		DESCRIPTION
			"The client retry count."
		::= { swAACServerInfoEntry 8 }

	swAACServerRowStatus OBJECT-TYPE
		SYNTAX      RowStatus
		MAX-ACCESS  read-create
		STATUS      current
		DESCRIPTION
			"This object indicates the status of this entry. A set request with
			RowStatus 'CreateAndGo' will fail when the current entry in the table 
			is equal to swAACMaxServer."
		::= { swAACServerInfoEntry 15 }

-- -----------------------------------------------------------------------------
-- swAACServerGroupCtrl OBJECT IDENTIFIER ::= { swAACMIB 15 }
-- -----------------------------------------------------------------------------
	swAACServerCtrlTable OBJECT-TYPE
		SYNTAX SEQUENCE OF SwAACServerCtrlEntry
		MAX-ACCESS not-accessible
		STATUS current
		DESCRIPTION
			"A table that is used to add/delete a server from the group."
		::= { swAACMIB 15 }

	swAACServerCtrlEntry OBJECT-TYPE
		SYNTAX SwAACServerCtrlEntry
		MAX-ACCESS not-accessible
		STATUS current
		DESCRIPTION
			"A table that is used to add/delete a server from group."
		INDEX { swAACCtrlServerGroupName,swAACCtrlServerAddrType,swAACCtrlServerIPAddr,swAACCtrlServerProtocol }
		::= { swAACServerCtrlTable 1 }

	SwAACServerCtrlEntry ::=
		SEQUENCE {
			swAACCtrlServerGroupName
				DisplayString,
			swAACCtrlServerAddrType
				InetAddressType,
			swAACCtrlServerIPAddr
				InetAddress,
			swAACCtrlServerProtocol
				INTEGER,
			swAACCtrlServerRowState
				INTEGER
		}

	swAACCtrlServerGroupName OBJECT-TYPE
		SYNTAX      DisplayString(SIZE(1..15))
		MAX-ACCESS  not-accessible
		STATUS      current
		DESCRIPTION
			"A human-readable text string of the method group."
		::= { swAACServerCtrlEntry 1 }

	swAACCtrlServerAddrType	OBJECT-TYPE
		SYNTAX		  InetAddressType
		MAX-ACCESS	  not-accessible
		STATUS		  current
		DESCRIPTION
			"The type of Server IP address.Only support ipv4(1) and ipv6(2)."
		::= { swAACServerCtrlEntry 2 }

	swAACCtrlServerIPAddr OBJECT-TYPE
		SYNTAX      InetAddress
		MAX-ACCESS  not-accessible
		STATUS      current
		DESCRIPTION
			"The IP address of the Server."
		::= { swAACServerCtrlEntry 3 }

	swAACCtrlServerProtocol OBJECT-TYPE
		SYNTAX      INTEGER{
			tacacs(1),
			xtacacs(2),
			tacacs-plus(3),
			radius(4)
		}
		MAX-ACCESS  not-accessible
		STATUS      current
		DESCRIPTION
			"The protocol provided by the Server."
		::= { swAACServerCtrlEntry 4 }

	swAACCtrlServerRowState OBJECT-TYPE
		SYNTAX      INTEGER{
			add(1),
			delete(2)
		}
		MAX-ACCESS  read-write
		STATUS      current
		DESCRIPTION
			"This object is used to add or delete an entry from swAACServerGroupTable."
		::= { swAACServerCtrlEntry 5 }

END
